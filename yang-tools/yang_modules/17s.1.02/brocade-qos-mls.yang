/*********************************************************************
 * Copyright (c) 2011 by Brocade Communications Systems, Inc.
 * All rights reserved.
 * brocade-qos.yang: Brocade QOS MLS module data model
 *
 * 2011-2016, Praveen Balachandra, Shivanand Tatpatti, Sabir Kunnathedath
 *
 *
 ********************************************************************/
module brocade-qos-mls {
  namespace "urn:brocade.com:mgmt:brocade-qos-mls";
  prefix qos-mls;

  import brocade-system-capabilities {
    prefix c;
  }
  import brocade-interface {
    prefix interface;
  }
  import brocade-common-def {
    prefix common-def;
  }

  organization "Brocade Communications Systems, Inc.";
  contact
    "Brocade Communications Systems, Inc.
     Postal: 130 Holger Way
             San Jose, CA 95134
             U.S.A
     Tel: +1-408-333-8000
     E-mail: support@Brocade.com 
     web: www.brocade.com.";
  description
    "This module manages Multi Layer Switching(MLS) Quality Of Service (QOS)";

  revision 2010-04-28 {
    description
      "Initial version of this management module.";
  }

  typedef dscp-id-range-type {
    type string {
      pattern "(([0-9])|([1-5][0-9])|(6[0-3]))(-(([0-9])|([1-5][0-9])|(6[0-3])))?((,(([0-9])|([1-5][0-9])|(6[0-3]))(-(([0-9])|([1-5][0-9])|(6[0-3])))?)?)*" {
        description
          "NUMBER:0-63;;DSCP Value/DSCP Range; Example: 0,1,2,4-7,8,9-22,55-63.";
      }
    }
  }

  typedef red-profile-id-type {
    type int32 {
      range "0 .. 383" {
        description
          "0-383;Profile id";
      }
    }
  }

  typedef map-name-type {
    type string {
      pattern "[a-zA-Z]{1}([-a-zA-Z0-9_]{0,63})";
    }
  }

  typedef cos-id-type {
    type uint8 {
      range "0 .. 7" {
        description
          "0-7;CoS";
      }
    }
  }

  typedef traffic-class-id-type {
    type uint8 {
      range "0 .. 7" {
        description
          "0-7;Traffic Class";
      }
    }
  }

  typedef drop-precedence-id-type {
    type uint8 {
      range "0 .. 3" {
        description
          "0-3;Drop Precedence";
      }
    }
  }

  typedef dscp-id-type {
    type uint8 {
      range "0 .. 63" {
        description
          "0-63;DSCP";
      }
    }
  }

  typedef min-queue-size-type {
    type uint32 {
      range "0 .. 1024";
    }
  }

  typedef max-queue-size-type {
    type uint32 {
      range "0 .. 6142";
    }
  }

  typedef guarantee-rate-type {
    type uint32 {
      range "0 .. 600000000";
    }
  }

  typedef best-effort-rate-type {
    type uint32 {
      range "0 .. 600000000";
    }
  }

  typedef rate-limit-percentage-type {
    type uint32 {
      range "0 .. 100";
    }
  }

  typedef rate-limit-bps-type {
    type uint64 {
      range "0 .. 100000000000";
    }
  }

  container qos {
    container map {
      list cos-mutation {
        key "name";
        leaf name {
          type map-name-type;
        }
        list cos-to-cos-mappings {
          key "from-cos";
          leaf from-cos {
            type cos-id-type;
          }
          container to {
            leaf to-cos {
              type cos-id-type;
            }
          }
        }
      }
      list cos-traffic-class {
        key "name";
        leaf name {
          type map-name-type;
        }
        list cos-to-tc-dp-mappings {
          key "from-cos";
          leaf from-cos {
            type cos-id-type;
          }
          container to {
            leaf to-traffic-class {
              type traffic-class-id-type;
            }
            leaf to-drop-precedence {
              type drop-precedence-id-type;
            }
          }
        }
      }
      list cos-dscp {
        key "name";
        leaf name {
          type map-name-type;
        }
        list cos-to-dscp-mappings {
          key "from-cos";
          leaf from-cos {
            type cos-id-type;
          }
          container to {
            leaf to-dscp {
              type dscp-id-type;
            }
          }
        }
      }
      list traffic-class-cos {
        key "traffic-class-cos-map-name";
        leaf traffic-class-cos-map-name {
          type map-name-type;
        }
        list tc-dp-to-cos-mapping {
          key "from-traffic-class from-drop-precedence";
          leaf from-traffic-class {
            type traffic-class-id-type;
          }
          leaf from-drop-precedence {
            description
              "In Drop-Precedence (Value 4 implies for all values of drop-precedence {0,1,2,3})";
            type drop-precedence-id-type;
          }
          container to {
            leaf to-cos {
              type cos-id-type;
            }
          }
        }
      }
      list traffic-class-mutation {
        key "name";
        leaf name {
          type map-name-type;
        }
        list traffic-class-mutation-mappings {
          key "from-traffic-class";
          leaf from-traffic-class {
            type traffic-class-id-type;
          }
          container to {
            leaf to-traffic-class {
              type traffic-class-id-type;
            }
          }
        }
      }
      list traffic-class-dscp {
        key "name";
        leaf name {
          type map-name-type;
        }
        list traffic-class-to-dscp-mappings {
          key "from-traffic-class";
          leaf from-traffic-class {
            type traffic-class-id-type;
          }
          container to {
            leaf to-dscp {
              type dscp-id-type;
            }
          }
        }
      }
      list dscp-mutation {
        key "dscp-mutation-map-name";
        leaf dscp-mutation-map-name {
          type map-name-type;
        }
        list dscp-to-dscp-mapping {
          key "dscp-in-values";
          leaf dscp-in-values {
            type dscp-id-range-type;
          }
          container to {
            leaf to-value {
              type dscp-id-type;
            }
          }
        }
      }
      list dscp-traffic-class {
        key "dscp-traffic-class-map-name";
        leaf dscp-traffic-class-map-name {
          type map-name-type;
        }
        list dscp-to-tc-dp-mapping {
          key "dscp-in-values";
          leaf dscp-in-values {
            type dscp-id-range-type;
          }
          container to {
            leaf to-value {
              type traffic-class-id-type;
            }
            leaf to-drop-precedence {
              type drop-precedence-id-type;
            }
          }
        }
      }
      list dscp-cos {
        key "dscp-cos-map-name";
        leaf dscp-cos-map-name {
          type map-name-type;
        }
        list dscp-to-cos-mapping {
          key "dscp-in-values";
          leaf dscp-in-values {
            type dscp-id-range-type;
          }
          container to {
            leaf to-value {
              type cos-id-type;
            }
          }
        }
      }
    }
    list red-profile {
      key "profile-id";
      leaf profile-id {
        type red-profile-id-type;
      }
      leaf min-threshold {
        mandatory true;
        type int32 {
          range "0 .. 100" {
            description
              "0-100;;Minimum threshold in percentage";
          }
        }
      }
      leaf max-threshold {
        mandatory true;
        type int32 {
          range "0 .. 100" {
            description
              "0-100;;Maximum threshold in percentage";
          }
        }
      }
      leaf drop-probability {
        mandatory true;
        type int32 {
          range "0 .. 100" {
            description
              "0-100;;Drop Probability in percentage";
          }
        }
      }
    }
    container tx-queue {
      leaf tx-queue-limit {
        when "(/c:capabilities/c:qos/c:system-tx-queue-limit = \"true\")";
        type uint32 {
          range "128 .. 8000";
        }
      }
      container scheduler {
        container strict-priority {
          leaf priority-number {
            type int32 {
              range "0 .. 7";
            }
          }
          leaf scheduler-type {
            type enumeration {
              enum "dwrr" {
                value 0;
              }
            }
          }
          leaf dwrr-traffic-class0 {
            type int32 {
              range "0 .. 100";
            }
          }
          leaf dwrr-traffic-class1 {
            type int32 {
              range "0 .. 100";
            }
          }
          leaf dwrr-traffic-class2 {
            type int32 {
              range "0 .. 100";
            }
          }
          leaf dwrr-traffic-class3 {
            type int32 {
              range "0 .. 100";
            }
          }
          leaf dwrr-traffic-class4 {
            type int32 {
              range "0 .. 100";
            }
          }
          leaf dwrr-traffic-class5 {
            type int32 {
              range "0 .. 100";
            }
          }
          leaf dwrr-traffic-class6 {
            type int32 {
              range "0 .. 100";
            }
          }
          leaf dwrr-traffic-class-last {
            type int32 {
              range "0 .. 100";
            }
          }
        }
      }
    }
    container rx-queue {
      when "(/c:capabilities/c:qos/c:system-rx-queue-limit = \"true\")";
      leaf rx-queue-limit {
        type uint32 {
          range "128 .. 8000";
        }
      }
    }
  }

  grouping po-phy-qos-config-group {
    leaf default-cos {
      type cos-id-type;
    }
    leaf default-tc {
      type traffic-class-id-type;
    }
    container trust {
      leaf trust-cos {
        type empty;
      }
      leaf trust-dscp {
        type empty;
      }
    }
    leaf cos-mutation {
      type map-name-type;
    }
    leaf traffic-class-cos {
      type map-name-type;
    }
    leaf cos-traffic-class {
      type map-name-type;
    }
    leaf dscp-mutation {
      type map-name-type;
    }
    leaf dscp-traffic-class {
      type map-name-type;
    }
    leaf dscp-cos {
      type map-name-type;
    }
    container random-detect {
      list traffic-class {
        key "red-tc-value";
        leaf red-tc-value {
          type traffic-class-id-type;
        }
        leaf red-profile-id {
          type uint32 {
            range "0 .. 383";
          }
          description
            "Keyword for all other VDX platforms";
        }
      }
    }
    container drop-monitor {
      leaf drop-monitor-enable {
        type empty;
      }
    }
    container flowcontrol {
      container link-level-flowcontrol {
        leaf flowcontrol-tx {
          type enumeration {
            enum "on" {
              value 1;
            }
            enum "off" {
              value 0;
            }
          }
        }
        leaf flowcontrol-rx {
          type enumeration {
            enum "on" {
              value 1;
            }
            enum "off" {
              value 0;
            }
          }
        }
      }
    }
  }

  grouping phy-qos-config-group {
    container rx-queue {
      when "(/c:capabilities/c:qos/c:conf-rx-queue-interface = \"true\")";
      description
        "Configure Ingress Queue Parameters";
      container unicast {
        list queue-size {
          key "traffic-class";
          leaf traffic-class {
            type traffic-class-id-type;
          }
          leaf min-queue-size {
            type min-queue-size-type;
          }
          leaf max-queue-size {
            type max-queue-size-type;
          }
        }
      }
      container multicast {
        leaf guarantee-rate {
          type guarantee-rate-type;
        }
        leaf best-effort-rate {
          type best-effort-rate-type;
        }
        list queue-size {
          key "traffic-class";
          leaf traffic-class {
            type traffic-class-id-type;
          }
          leaf min-queue-size {
            type min-queue-size-type;
          }
          leaf max-queue-size {
            type max-queue-size-type;
          }
        }
      }
    }
  }

  grouping phy-bum-storm-control-config {
    container storm-control {
      list ingress {
        key "protocol-type";
        leaf protocol-type {
          type enumeration {
            enum "broadcast" {
              value 1;
            }
            enum "multicast" {
              value 2;
            }
            enum "unknown-unicast" {
              value 3;
            }
          }
        }
        leaf rate-format {
          type enumeration {
            enum "limit-bps" {
              value 1;
            }
            enum "limit-percent" {
              value 2;
            }
          }
        }
        leaf rate-bps {
          type rate-limit-bps-type;
        }
        leaf rate-percent {
          type rate-limit-percentage-type;
        }
        leaf bum-action {
          type enumeration {
            enum "monitor" {
              value 2;
            }
            enum "shutdown" {
              value 3;
            }
          }
        }
      }
    }
  }

  augment "/interface:interface/interface:ethernet" {
    uses phy-bum-storm-control-config;
    container qos {
      uses po-phy-qos-config-group;
      uses phy-qos-config-group;
    }
  }
  augment "/interface:interface/interface:port-channel" {
    container qos {
      uses po-phy-qos-config-group;
    }
  }
  augment "/common-def:routing-system/interface:interface/interface:ve" {
    container qos {
      leaf dscp-cos {
        type map-name-type;
      }
      leaf dscp-mutation {
        type map-name-type;
      }
      leaf dscp-traffic-class {
        type map-name-type;
      }
    }
  }
}
