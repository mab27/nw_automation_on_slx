/****************************************************************
* Copyright (c) 2014 by Brocade Communications Systems, Inc.
* All rights reserved.
* brocade-sysmgr.yang: Brocade System Manager Data Model
*
* July 2015, Tejaswi Haramurali
*
*****************************************************************/
module brocade-sysmgr {
  namespace "urn:brocade.com:mgmt:brocade-sysmgr";
  prefix sysmgr;

  import tailf-common {
    prefix tailf;
  }
  import brocade-common-def {
    prefix common-def;
  }

  contact
    "Brocade Communications Systems, Inc.
     Postal: 130 Holger Way
             San Jose, CA 95134
              U.S.A
     Tel: +1-408-333-8000
     E-mail: support@Brocade.com
     web: www.brocade.com.";
  description
    "This system manager  module is used to display the bpswitch statistics
     for the switch";

  revision 2015-07-22 {
    description
      "Initial version of this management module.";
  }

  augment "/common-def:show" {
    container bpswitch {
      container show-stats {
        tailf:action "stats" {
          input {
            choice show-bpswitch-type {
              case stats1 {
                leaf port {
                  type uint32 {
                    range "1 .. 20" {
                      error-message "Port number must be in the range 1..20";
                    }
                  }
                }
              }
              case stats2 {
                leaf global {
                  type empty;
                }
              }
            }
          }
          output;
        }
      }
    }
  }
  augment "/common-def:clear" {
    container bpswitch {
      tailf:action "clear-stats" {
        description
          "Clear bpswitch stats info";
        input;
        output;
      }
    }
  }
}
