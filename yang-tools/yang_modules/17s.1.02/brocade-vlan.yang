/*********************************************************************
 * Copyright (c) 2011 by Brocade Communications Systems, Inc.
 * All rights reserved.
 *brocade-vlan.yang: Brocade vlan classifier module data model
 *
 * Mar 2011, Raghuprem Muthigi
 *
 *
 ********************************************************************/
module brocade-vlan {
  namespace "urn:brocade.com:mgmt:brocade-vlan";
  prefix brocade-vlan;

  organization "Brocade Communications Systems, Inc.";
  contact
    "Brocade Communications Systems, Inc.
     Postal: 130 Holger Way
             San Jose, CA 95134
             U.S.A
     Tel: +1-408-333-8000
     E-mail: support@Brocade.com
     web: www.brocade.com.";
  description
    "This submodule manages VLAN related CLIs.";

  revision 2016-02-23 {
    description
      "Removed vlan-classifier related CLIs.";
  }
  revision 2009-12-10 {
    description
      "Initial Version of this management module.";
  }

  container vlan {
    container dot1q {
      container tag {
        leaf native {
          type empty;
        }
      }
    }
  }
}
