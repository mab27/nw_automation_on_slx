/*********************************************************************
 * Copyright (c) 2014 by Brocade Communications Systems, Inc.
 * All rights reserved.
 * brocade-distributedlog.yang: Brocade Event Handler Data Model
 *
 * November 2014, Brian Adaniya 
 *
 *
 ********************************************************************/
module brocade-event-handler {
  namespace "urn:brocade.com:mgmt:brocade-event-handler";
  prefix event-handler;

  import tailf-common {
    prefix tailf;
  }
  import brocade-common-def {
    prefix common-def;
  }

  organization "Brocade Communications Inc.";
  contact
    "Brocade Communications Systems, Inc.
     Postal: 130 Holger Way,
     San Jose, CA 95134
     U.S.A
     Tel: +1-408-333-8000
     E-mail: support@Brocade.com
     web: www.brocade.com.";
  description
    "event handler related information";
  reference "<Author Name>, '<Title>', <RFC XXXX>, <Month> <YEAR>.";

  revision 2010-12-02 {
    description
      "Initial version";
  }

  grouping event-handler-group {
    list event-handler-list {
      key "name";
      leaf name {
        type common-def:name-string32;
        description
          "Event handler name";
      }
      leaf description {
        type string {
          length "1 .. 128";
        }
        description
          "Event handler description (Max Size - 128)";
      }
      list trigger {
        description
          "VCS event or RASlog event.";
        key "trigger-id";
        leaf trigger-id {
          type uint32 {
            range "1..100" {
              error-message "% Error: Value out of range at '^' marker";
            }
          }
        }
        choice trigger-choice {
          case raslog {
            container raslog {
              description
                "RASlog Id.";
              leaf raslog {
                description
                  "RASlog Id.";
                type common-def:name-string32;
              }
              leaf pattern {
                description
                  "Regular expression trigger filter.";
                type string {
                  length "1 .. 128";
                }
              }
            }
          }
        }
      }
      container action {
        choice action-choice {
          case python-script {
            leaf python-script {
              description
                "Name of a script located under the flash:// directory (Max Size - 32).";
              type common-def:name-string32;
            }
          }
        }
      }
    }
  }

  grouping event-handler-activation {
    list name {
      key "name";
      leaf name {
        type common-def:name-string32;
        description
          "Event handler name";
      }
      leaf delay {
        type uint32;
        default "0";
      }
      leaf iterations {
        type uint32;
        default "1";
      }
      leaf interval {
        type uint32;
        default "0";
      }
      leaf trigger-mode {
        type enumeration {
          enum "each-instance" {
            value 1;
          }
          enum "on-first-instance" {
            value 2;
          }
          enum "only-once" {
            value 3;
          }
        }
        default "each-instance";
      }
      container trigger-function {
        description
          "Trigger-function controls how multiple triggers are interpreted to launch the action (default = OR).";
        leaf trigger-function {
          type enumeration {
            enum "OR" {
              value 1;
            }
            enum "AND" {
              value 2;
            }
          }
          default "OR";
        }
        leaf time-window {
          when "(../trigger-function = 'AND') or (../trigger-function = '2')";
          type uint32;
          mandatory true;
        }
      }
      leaf action-timeout {
        type uint32;
        default "0";
      }
    }
  }

  grouping event-handler-actions-group {
    tailf:action "abort" {
      input {
        leaf action {
          type common-def:name-string32;
          mandatory true;
        }
      }
    }
  }

  container event-handler {
    description
      "Event Handler Commands";
    uses event-handler-group;
    uses event-handler-actions-group;
    container activate {
      uses event-handler-activation;
    }
  }
  augment "/common-def:show" {
    container event-handler {
      tailf:action "activations" {
        input;
      }
    }
  }
}
