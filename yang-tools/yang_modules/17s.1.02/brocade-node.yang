/*********************************************************************
 * Copyright (c) 2017 by Brocade Communications Systems, Inc.
 * All rights reserved.
 * brocade-node.yang: Brocade node Data model.
 *
 * Feb 2017, Mithun B S
 *
 *
 ********************************************************************/
module brocade-node {
  namespace "urn:brocade.com:mgmt:brocade-node";
  prefix node;

  organization "Brocade Communications Systems, Inc.";
  contact
    "Brocade Communications Systems, Inc.
     Postal: 130 Holger Way
             San Jose, CA 95134
              U.S.A
     Tel: +1-408-333-8000
     E-mail: support@Brocade.com 
     web: www.brocade.com.";
  description
    "This management module is an instrumentation to manage 
     node-id feature.";

  revision 2017-02-08 {
    description
      "Initial version of this management module
       brocade-node.";
  }

  list node-id {
    key "node-id";
    leaf node-id {
      type uint32;
    }
  }
}
