/*********************************************************************
 * Copyright (c) 2010 by Brocade Communications Systems, Inc.
 * All rights reserved.
 * brocade-lacp.yang: Brocade LACP data model
 *
 * January 2010, Mobin Mohan
 *
 *
 ********************************************************************/
module brocade-lacp {
  namespace "urn:brocade.com:mgmt:brocade-lacp";
  prefix lacp;

  import brocade-interface {
    prefix interface;
  }

  organization "Brocade Communications Systems, Inc.";
  contact
    "Brocade Communications Systems, Inc.
     Postal: 1745 Technology Drive,
             San Jose, CA 95110 
              U.S.A
     Tel: +1-408-392-6061
     E-mail: support@Brocade.com 
     web: www.brocade.com.";
  description
    "This module describes the data model for Link Aggregation 
     Control Protocol";

  revision 2010-01-25 {
    description
      "Initial Version";
  }

  container lacp {
    leaf system-priority {
      type uint32 {
        range "1 .. 65535";
      }
      default "32768";
    }
  }

  grouping common-phy-lacp-cmds {
    container lacp {
      leaf timeout {
        type enumeration {
          enum "short" {
            value 1;
          }
          enum "long" {
            value 2;
          }
        }
      }
      leaf std_port-priority {
        description
          "This command is used to configure port priority";
        type uint32 {
          range "1 .. 65535";
        }
        default "32768";
      }
      leaf default-up {
        type empty;
      }
    }
  }

  augment "/interface:interface/interface:ethernet" {
    uses common-phy-lacp-cmds;
  }
}
