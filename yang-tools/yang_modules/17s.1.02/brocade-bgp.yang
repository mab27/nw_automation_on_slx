/*********************************************************************
 * Copyright (c) 2011 by Brocade Communications Systems, Inc.
 * All rights reserved.
 * brocade-bgp.yang: Brocade BGP data model
 *
 *
 *
 ********************************************************************/
module brocade-bgp {
  namespace "urn:brocade.com:mgmt:brocade-bgp";
  prefix bgp;

  import brocade-common-def {
    prefix common-def;
  }
  import ietf-inet-types {
    prefix inet;
  }
  import brocade-interface {
    prefix interface;
  }
  import brocade-tunnels {
    prefix tunnels;
  }
  import brocade-system-capabilities {
    prefix c;
  }
  import brocade-bfd {
    prefix bfd;
  }
  import brocade-bridge-domain {
    prefix bridge-domain;
  }

  organization "Brocade Communications Systems, Inc.";
  contact
    "Brocade Communications Systems, Inc.
     Postal: 130 Holger Way,
             San Jose, CA 95134
              U.S.A
     Tel: +1-408-333-8000
     E-mail: support@Brocade.com
     web: www.brocade.com.";
  description
    "This management module is an instrumentation to manage
     BGP Protocol.";

  revision 2010-11-29 {
    description
      "Initial version of this management module.";
  }

  typedef neighbor-description {
    type string {
      length "1..220";
    }
  }

  typedef rd-rt-type {
    type string {
      pattern "(((([1-9][0-9]{0,3})|([1-5][0-9]{4})|(6[0-4][0-9]{3})|(65[0-4][0-9]{2})|(655[0-2][0-9])|(6553[0-5])):(([0-9][0-9]{0,8})|([1-3][0-9]{9})|(4[0-1][0-9]{8})|(42[0-8][0-9]{7})|(429[0-3][0-9]{6})|(4294[0-8][0-9]{5})|(42949[0-5][0-9]{4})|(429496[0-6][0-9]{3})|(4294967[0-1][0-9]{2})|(42949672[0-8][0-9])|(429496729[0-5])))|((([1-9][0-9]{0,8})|(4[0-1][0-9]{8})|(42[0-8][0-9]{7})|(429[0-3][0-9]{6})|(4294[0-8][0-9]{5})|(42949[0-5][0-9]{4})|(429496[0-6][0-9]{3})|(4294967[0-1][0-9]{2})|(42949672[0-8][0-9])):(([1-9][0-9]{0,3})|([1-5][0-9]{4})|(6[0-4][0-9]{3})|(65[0-4][0-9]{2})|(655[0-2][0-9])|(6553[0-5])))|(((([1-9]|[1-9][0-9]|1[0-9]{2}|2[0-4][0-9]|25[0-5])\\.)(([0-9]|[1-9][0-9]|1[0-9]{2}|2[0-4][0-9]|25[0-5])\\.){2}([0-9]|[1-9][0-9]|1[0-9]{2}|2[0-4][0-9]|25[0-5])):(([1-9][0-9]{0,3})|([1-5][0-9]{4})|(6[0-4][0-9]{3})|(65[0-4][0-9]{2})|(655[0-2][0-9])|(6553[0-5]))))";
    }
  }

  typedef rt-type {
    type string {
      pattern "auto";
    }
  }

  typedef additional-paths-best {
    type uint32 {
      range "1..5";
    }
  }

  typedef evpn-type {
    type string {
      pattern "[a-zA-Z]{1}([-a-zA-Z0-9_]{0,63})";
    }
  }

  typedef attribute-map {
    type string {
      length "1..63";
    }
  }

  typedef advertise-map {
    type string {
      length "1..63";
    }
  }

  typedef suppress-map {
    type string {
      length "1..63";
    }
  }

  typedef delay-timer {
    type uint32 {
      range "3..10";
    }
  }

  typedef max-count {
    type uint32 {
      range "3..10";
    }
  }

  typedef dup-mac-timer {
    type uint32 {
      range "5..300";
    }
  }

  typedef local-preference-number {
    type uint32 {
      range "1..65535";
    }
  }

  typedef default-metric-number {
    type uint32 {
      range "1..4294967295";
    }
  }

  typedef rib-route-number {
    type uint32 {
      range "1..4294967295";
    }
  }

  typedef decimal-number {
    type uint32 {
      range "1..65535";
    }
  }

  typedef absolute-decimal-number {
    type uint32 {
      range "0..65535";
    }
  }

  typedef update-time-type {
    type uint32 {
      range "0..30";
    }
  }

  typedef cidentifier {
    type uint32 {
      range "1..4294967295";
    }
  }

  typedef htime {
    type uint32 {
      range "1..45";
    }
  }

  typedef damp-reuse-value {
    type uint32 {
      range "1..20000";
    }
  }

  typedef damp-start-suppress-value {
    type uint32 {
      range "1..20000";
    }
  }

  typedef damp-max-suppress-value {
    type uint32 {
      range "1..255";
    }
  }

  typedef rmap-type {
    type string {
      length "1..63";
    }
  }

  typedef ext-route-distance {
    type uint32 {
      range "1..255";
    }
  }

  typedef int-route-distance {
    type uint32 {
      range "1..255";
    }
  }

  typedef lcl-route-distance {
    type uint32 {
      range "1..255";
    }
  }

  typedef local-as-type {
    type string {
      pattern "((([0-9][0-9]{0,3})|([1-5][0-9]{4})|(6[0-4][0-9]{3})|(65[0-4][0-9]{2})|(655[0-2][0-9])|(6553[0-5]))\\.(([0-9][0-9]{0,3})|([1-5][0-9]{4})|(6[0-4][0-9]{3})|(65[0-4][0-9]{2})|(655[0-2][0-9])|(6553[0-5])))|([1-9][0-9]{0,8})|([1-3][0-9]{9})|(4[0-1][0-9]{8})|(42[0-8][0-9]{7})|(429[0-3][0-9]{6})|(4294[0-8][0-9]{5})|(42949[0-5][0-9]{4})|(429496[0-6][0-9]{3})|(4294967[0-1][0-9]{2})|(42949672[0-8][0-9])|(429496729[0-5])";
    }
  }

  typedef num-as-in-path {
    type uint32 {
      range "0..300";
    }
  }

  typedef ebgp-paths {
    type uint32 {
      range "1..64";
    }
  }

  typedef ibgp-paths {
    type uint32 {
      range "1..64";
    }
  }

  typedef conn-metric {
    type uint32 {
      range "1..4294967295";
    }
  }

  typedef sdistance {
    type uint32 {
      range "1..255";
    }
  }

  typedef adv-value {
    type uint32 {
      range "0..3600";
    }
  }

  typedef ip-filter-name {
    type string {
      length "1..63";
    }
  }

  typedef local-as-num {
    type string {
      pattern "((([0-9][0-9]{0,3})|([1-5][0-9]{4})|(6[0-4][0-9]{3})|(65[0-4][0-9]{2})|(655[0-2][0-9])|(6553[0-5]))\\.(([0-9][0-9]{0,3})|([1-5][0-9]{4})|(6[0-4][0-9]{3})|(65[0-4][0-9]{2})|(655[0-2][0-9])|(6553[0-5])))|([1-9][0-9]{0,8})|([1-3][0-9]{9})|(4[0-1][0-9]{8})|(42[0-8][0-9]{7})|(429[0-3][0-9]{6})|(4294[0-8][0-9]{5})|(42949[0-5][0-9]{4})|(429496[0-6][0-9]{3})|(4294967[0-1][0-9]{2})|(42949672[0-8][0-9])|(429496729[0-5])";
    }
  }

  typedef num-as-in-as-path {
    type uint32 {
      range "0..300";
    }
  }

  typedef max-prefix-limit {
    type uint32 {
      range "1..2147483647";
    }
  }

  typedef max-prefix-threshold {
    type uint32 {
      range "1..100";
    }
  }

  typedef bgp-password {
    type string;
  }

  typedef bgp-peergroup {
    type string {
      pattern "[a-zA-Z]{1}([-a-zA-Z0-9\\\\\\\\@#\\+\\*\\(\\)=\\{~\\}%<>=$_\\[\\]\\|]{0,62})";
    }
  }

  typedef nei-prefix-list-filter {
    type string {
      length "1..63";
    }
  }

  typedef bgp-remote-as {
    type string {
      pattern "((([0-9][0-9]{0,3})|([1-5][0-9]{4})|(6[0-4][0-9]{3})|(65[0-4][0-9]{2})|(655[0-2][0-9])|(6553[0-5]))\\.(([0-9][0-9]{0,3})|([1-5][0-9]{4})|(6[0-4][0-9]{3})|(65[0-4][0-9]{2})|(655[0-2][0-9])|(6553[0-5])))|([1-9][0-9]{0,8})|([1-3][0-9]{9})|(4[0-1][0-9]{8})|(42[0-8][0-9]{7})|(429[0-3][0-9]{6})|(4294[0-8][0-9]{5})|(42949[0-5][0-9]{4})|(429496[0-6][0-9]{3})|(4294967[0-1][0-9]{2})|(42949672[0-8][0-9])|(429496729[0-5])";
    }
  }

  typedef nei-keep-alive {
    type uint32 {
      range "0..65535";
    }
  }

  typedef nei-hold-time {
    type uint32 {
      range "0..65535";
    }
  }

  typedef sip-ipv6-address {
    type inet:ipv6-address;
  }

  typedef sip-ipv4-address {
    type inet:ipv4-address;
  }

  typedef loopback-interface {
    type string {
      length "1..63";
    }
  }

  typedef nei-weight {
    type uint32 {
      range "0..65535";
    }
  }

  typedef encapsulation-t {
    type enumeration {
      enum "mpls" {
        value 1;
        description
          "MPLS encapsulation.";
      }
      enum "vxlan" {
        value 2;
        description
          "VXLAN encapsulation.";
      }
      enum "nsh" {
        value 3;
        description
          "NSH encapsulation.";
      }
    }
  }

  typedef update-source-ethernet-type {
    type string {
      pattern "((([0-9]|[1][0-6]))/([1-9]|[1-9][0-9])(:[1-4])?)";
      length "3..16";
    }
    description
      "The definition for specifying a network interface name in
       a VCS environment. It is in 3-tuple canonical format:
       rbridge-id/slot/port.";
  }

  typedef rd-type {
    type string;
  }

  grouping common-maxas-limit-group {
    container maxas-limit {
      container in {
        choice ch-maxas-limit {
          case ca-maxas-limit-enable {
            leaf num-as-in-as-path {
              type num-as-in-as-path;
            }
          }
          case ca-maxas-limit-disable {
            leaf maxas-limit-disable {
              type empty;
            }
          }
        }
      }
    }
  }

  grouping common-maximum-paths-grouping {
    container maximum-paths {
      leaf load-sharing-value {
        type uint32 {
          range "1..64";
        }
      }
      leaf ebgp {
        type ebgp-paths;
      }
      leaf ibgp {
        type ibgp-paths;
      }
      leaf use-load-sharing {
        type empty;
      }
    }
  }

  grouping af-ipv6-network-cmds {
    list network {
      key "network-ipv6-address";
      leaf network-ipv6-address {
        type inet:ipv6-prefix;
      }
      uses af-common-network-cmds;
    }
  }

  grouping af-ipv4-network-cmds {
    list network {
      key "network-ipv4-address";
      leaf network-ipv4-address {
        type inet:ipv4-prefix;
      }
      uses af-common-network-cmds;
    }
  }

  grouping af-common-network-cmds {
    leaf network-weight {
      type absolute-decimal-number;
    }
    leaf backdoor {
      type empty;
    }
    leaf network-route-map {
      type rmap-type;
    }
  }

  grouping evpn-mode-attributes {
    leaf client-to-client-reflection {
      type empty;
    }
    uses graceful-restart-cmds;
    container retain {
      container route-target {
        leaf all {
          type empty;
        }
      }
    }
    leaf vtep-discovery {
      type empty;
    }
  }

  grouping evpn-neighbor-attributes {
    leaf encapsulation {
      type encapsulation-t;
    }
    leaf maximum-prefix {
      type max-prefix-limit;
    }
    leaf route-reflector-client {
      type empty;
    }
    leaf allowas-in {
      type uint32 {
        range "1..10";
      }
    }
    leaf next-hop-unchanged {
      type empty;
    }
    leaf enable-peer-as-check {
      type empty;
    }
    container route-map {
      container direction-in {
        leaf route-map-name-direction-in {
          type common-def:name-string64;
        }
      }
      container direction-out {
        leaf route-map-name-direction-out {
          type common-def:name-string64;
        }
      }
    }
    leaf activate {
      type empty;
    }
  }

  grouping advertise-additional-paths {
    container additional-paths {
      container advertise {
        choice ch-additional-paths {
          case ca-best {
            leaf best {
              type additional-paths-best;
            }
          }
          case ca-all {
            leaf all {
              type empty;
            }
          }
        }
      }
    }
  }

  grouping address-family-group {
    container address-family {
      container ipv4 {
        container ipv4-unicast {
          container default-vrf {
            leaf default-vrf-selected {
              type empty;
            }
            uses af-ipv4-uc-cmds;
          }
          list af-vrf {
            key "af-vrf-name";
            leaf af-vrf-name {
              type string {
                length "1..255";
              }
            }
            leaf local-as {
              type local-as-type;
            }
            container maxas-limit {
              container in {
                leaf num-as-in-path {
                  type num-as-in-path;
                }
              }
            }
            leaf next-hop-recursion {
              type empty;
            }
            leaf graceful-restart-status {
              type empty;
            }
            uses af-ipv4-uc-vrf-cmds;
          }
        }
      }
      container ipv6 {
        container ipv6-unicast {
          container default-vrf {
            leaf default-vrf-selected {
              type empty;
            }
            uses af-ipv6-uc-cmds;
          }
          list af-ipv6-vrf {
            key "af-ipv6-vrf-name";
            leaf af-ipv6-vrf-name {
              type string {
                length "1..255";
              }
            }
            leaf next-hop-recursion {
              type empty;
            }
            leaf graceful-restart-status {
              type empty;
            }
            uses af-ipv6-uc-vrf-cmds;
          }
        }
      }
      container l2vpn {
        container evpn {
          presence "true";
          uses evpn-mode-attributes;
          container neighbor {
            list evpn-peer-group {
              key "evpn-neighbor-peergroup-name";
              leaf evpn-neighbor-peergroup-name {
                type bgp-peergroup;
              }
              uses evpn-neighbor-attributes;
              container send-community {
                leaf send-community-status {
                  type empty;
                }
                leaf both {
                  type empty;
                }
                leaf extended {
                  type empty;
                }
                leaf standard {
                  type empty;
                }
              }
            }
            list evpn-neighbor-ipv4 {
              key "evpn-neighbor-ipv4-address";
              leaf evpn-neighbor-ipv4-address {
                type inet:ipv4-address;
              }
              uses evpn-neighbor-attributes;
              container send-community {
                leaf send-community-status {
                  type empty;
                }
                leaf both {
                  type empty;
                }
                leaf extended {
                  type empty;
                }
                leaf standard {
                  type empty;
                }
              }
            }
            list evpn-neighbor-ipv6 {
              key "evpn-neighbor-ipv6-address";
              leaf evpn-neighbor-ipv6-address {
                type inet:ipv6-address;
              }
              uses evpn-neighbor-attributes;
              container send-community {
                leaf send-community-status {
                  type empty;
                }
                leaf both {
                  type empty;
                }
                leaf extended {
                  type empty;
                }
                leaf standard {
                  type empty;
                }
              }
            }
          }
        }
      }
    }
  }

  grouping af-ipv6-neighbor-cmds {
    container neighbor {
      container af-ipv6-neighbor-peergroup-holder {
        list af-ipv6-neighbor-peergroup {
          key "af-ipv6-neighbor-peergroup-name";
          leaf af-ipv6-neighbor-peergroup-name {
            type bgp-peergroup;
          }
          container send-community {
            leaf send-community-status {
              type empty;
            }
            leaf both {
              type empty;
            }
            leaf extended {
              type empty;
            }
            leaf standard {
              type empty;
            }
          }
          container af-neighbor-capability {
            container orf {
              container prefixlist {
                leaf prefixlist-status {
                  type empty;
                  description
                    "This element will be set if either(or both) send,receive options are configured";
                }
                leaf prefixlist-send {
                  type empty;
                  description
                    "Capability to SEND the ORF to this neighbor";
                }
                leaf prefixlist-receive {
                  type empty;
                  description
                    "Capability to RECEIVE the ORF from this neighbor";
                }
              }
            }
            container additional-paths {
              leaf add-path-both {
                type empty;
              }
              leaf send {
                type empty;
              }
              leaf receive {
                type empty;
              }
            }
          }
          uses advertise-additional-paths;
          leaf activate {
            type empty;
          }
          uses af-neighbor-cmds;
        }
      }
      container af-ipv6-neighbor-address-holder {
        list af-ipv6-neighbor-address {
          key "af-ipv6-neighbor-address";
          leaf af-ipv6-neighbor-address {
            type inet:ipv6-address;
          }
          container send-community {
            description
              "TODO default is standard.if extended is set, then the show run has to render the value as both";
            leaf send-community-status {
              type empty;
            }
            leaf both {
              type empty;
            }
            leaf extended {
              type empty;
            }
            leaf standard {
              type empty;
            }
          }
          container af-neighbor-capability {
            container orf {
              container prefixlist {
                leaf prefixlist-status {
                  type empty;
                  description
                    "This element will be set if either(or both) send,receive options are configured";
                }
                leaf prefixlist-send {
                  type empty;
                  description
                    "Capability to SEND the ORF to this neighbor";
                }
                leaf prefixlist-receive {
                  type empty;
                  description
                    "Capability to RECEIVE the ORF from this neighbor";
                }
              }
            }
            container additional-paths {
              leaf add-path-both {
                type empty;
              }
              leaf send {
                type empty;
              }
              leaf receive {
                type empty;
              }
            }
          }
          uses advertise-additional-paths;
          leaf activate {
            type empty;
          }
          uses af-neighbor-cmds;
        }
      }
    }
  }

  grouping af-ipv4-vrf-neighbor-cmds {
    container neighbor {
      container af-ipv4-vrf-neighbor-address-holder {
        list af-ipv4-neighbor-addr {
          key "af-ipv4-neighbor-address";
          leaf af-ipv4-neighbor-address {
            type inet:ipv4-address;
          }
          leaf associate-peer-group {
            type bgp-peergroup;
          }
          uses vrf-neighbor-cmds;
          container af-vrf-neighbor-capability {
            uses as4-capability-cmd;
            container orf {
              container prefixlist {
                leaf prefixlist-status {
                  type empty;
                  description
                    "This element will be set if either(or both) send,receive options are configured";
                }
                leaf prefixlist-send {
                  type empty;
                  description
                    "Capability to SEND the ORF to this neighbor";
                }
                leaf prefixlist-receive {
                  type empty;
                  description
                    "Capability to RECEIVE the ORF from this neighbor";
                }
              }
            }
            container additional-paths {
              leaf add-path-both {
                type empty;
              }
              leaf send {
                type empty;
              }
              leaf receive {
                type empty;
              }
            }
          }
          uses router-bgp-neighbor-attributes;
          uses common-maxas-limit-group;
          uses ipv4-update-source-cmd;
          uses advertise-additional-paths;
          container send-community {
            leaf send-community-status {
              type empty;
            }
            leaf both {
              type empty;
            }
            leaf extended {
              type empty;
            }
            leaf standard {
              type empty;
            }
          }
        }
      }
    }
  }

  grouping af-ipv6-vrf-neighbor-cmds {
    container neighbor {
      container af-ipv6-vrf-neighbor-address-holder {
        list af-ipv6-neighbor-addr {
          key "af-ipv6-neighbor-address";
          leaf af-ipv6-neighbor-address {
            type inet:ipv6-address;
          }
          leaf associate-peer-group {
            type bgp-peergroup;
          }
          uses vrf-neighbor-cmds;
          container af-vrf-neighbor-capability {
            uses as4-capability-cmd;
            container orf {
              container prefixlist {
                leaf prefixlist-status {
                  type empty;
                  description
                    "This element will be set if either(or both) send,receive options are configured";
                }
                leaf prefixlist-send {
                  type empty;
                  description
                    "Capability to SEND the ORF to this neighbor";
                }
                leaf prefixlist-receive {
                  type empty;
                  description
                    "Capability to RECEIVE the ORF from this neighbor";
                }
              }
            }
            container additional-paths {
              leaf add-path-both {
                type empty;
              }
              leaf send {
                type empty;
              }
              leaf receive {
                type empty;
              }
            }
          }
          uses common-maxas-limit-group;
          uses advertise-additional-paths;
          uses router-bgp-neighbor-attributes;
          uses ipv6-update-source-cmd;
          container send-community {
            leaf send-community-status {
              type empty;
            }
            leaf both {
              type empty;
            }
            leaf extended {
              type empty;
            }
            leaf standard {
              type empty;
            }
          }
        }
      }
    }
  }

  grouping vrf-neighbor-cmds {
    leaf remote-as {
      type bgp-remote-as;
    }
    container shutdown {
      leaf shutdown-status {
        type empty;
      }
      leaf generate-rib-out {
        type empty;
      }
    }
    leaf activate {
      type empty;
    }
    uses af-neighbor-cmds;
  }

  grouping ipv6-update-source-cmd {
    container update-source {
      choice ch-update-source {
        case ca-ipv6 {
          leaf sip-ipv6-address {
            type sip-ipv6-address;
          }
        }
        case ca-eth {
          container ethernet-interface {
            leaf interface-type {
              type enumeration {
                enum "ethernet" {
                  value 1;
                }
              }
            }
            leaf interface-name {
              type update-source-ethernet-type;
            }
          }
        }
        case ca-port-channel {
          leaf port-channel {
            type interface:portchannel-type;
          }
        }
        case ca-loopback {
          leaf loopback {
            type loopback-interface;
          }
        }
        case ca-ve {
          leaf ve-interface {
            type interface:ve-type;
          }
        }
      }
    }
  }

  grouping ipv4-update-source-cmd {
    container update-source {
      choice ch-update-source {
        case ca-ipv4 {
          leaf sip-ipv4-address {
            type sip-ipv4-address;
          }
        }
        case ca-eth {
          container ethernet-interface {
            leaf interface-type {
              type enumeration {
                enum "ethernet" {
                  value 1;
                }
              }
            }
            leaf interface-name {
              type update-source-ethernet-type;
            }
          }
        }
        case ca-port-channel {
          leaf port-channel {
            type interface:portchannel-type;
          }
        }
        case ca-loopback {
          leaf loopback {
            type loopback-interface;
          }
        }
        case ca-ve {
          leaf ve-interface {
            type interface:ve-type;
          }
        }
      }
    }
  }

  grouping as4-capability-cmd {
    container as4 {
      leaf neighbor-as4-enable {
        type empty;
      }
      leaf neighbor-as4-disable {
        type empty;
      }
    }
  }

  grouping af-ipv4-neighbor-cmds {
    container neighbor {
      container af-ipv4-neighbor-peergroup-holder {
        list af-ipv4-neighbor-peergroup {
          key "af-ipv4-neighbor-peergroup-name";
          leaf af-ipv4-neighbor-peergroup-name {
            type bgp-peergroup;
          }
          container send-community {
            leaf send-community-status {
              type empty;
            }
            leaf both {
              type empty;
            }
            leaf extended {
              type empty;
            }
            leaf standard {
              type empty;
            }
          }
          container af-neighbor-capability {
            container orf {
              container prefixlist {
                leaf prefixlist-status {
                  type empty;
                  description
                    "This element will be set if either(or both) send,receive options are configured";
                }
                leaf prefixlist-send {
                  type empty;
                  description
                    "Capability to SEND the ORF to this neighbor";
                }
                leaf prefixlist-receive {
                  type empty;
                  description
                    "Capability to RECEIVE the ORF from this neighbor";
                }
              }
            }
            container additional-paths {
              leaf add-path-both {
                type empty;
              }
              leaf send {
                type empty;
              }
              leaf receive {
                type empty;
              }
            }
          }
          uses advertise-additional-paths;
          leaf activate {
            type empty;
          }
          uses af-neighbor-cmds;
        }
      }
      container af-ipv4-neighbor-address-holder {
        list af-ipv4-neighbor-address {
          key "af-ipv4-neighbor-address";
          leaf af-ipv4-neighbor-address {
            type inet:ipv4-address;
          }
          container send-community {
            leaf send-community-status {
              type empty;
            }
            leaf both {
              type empty;
            }
            leaf extended {
              type empty;
            }
            leaf standard {
              type empty;
            }
          }
          container af-neighbor-capability {
            container orf {
              container prefixlist {
                leaf prefixlist-status {
                  type empty;
                  description
                    "This element will be set if either(or both) send,receive options are configured";
                }
                leaf prefixlist-send {
                  type empty;
                  description
                    "Capability to SEND the ORF to this neighbor";
                }
                leaf prefixlist-receive {
                  type empty;
                  description
                    "Capability to RECEIVE the ORF from this neighbor";
                }
              }
            }
            container additional-paths {
              leaf add-path-both {
                type empty;
              }
              leaf send {
                type empty;
              }
              leaf receive {
                type empty;
              }
            }
          }
          uses advertise-additional-paths;
          leaf activate {
            type empty;
          }
          uses af-neighbor-cmds;
        }
      }
    }
  }

  grouping af-neighbor-cmds {
    leaf allowas-in {
      type uint32 {
        range "1..10";
      }
    }
    leaf enable-peer-as-check {
      type empty;
    }
    container filter-list {
      container direction-in {
        leaf filter-list-direction-in-acl-name {
          type ip-filter-name;
        }
        leaf filter-list-name-direction-in {
          type empty;
        }
      }
      container direction-out {
        leaf filter-list-direction-out-acl-name {
          type ip-filter-name;
        }
        leaf filter-list-name-direction-out {
          type empty;
        }
      }
    }
    container maximum-prefix {
      leaf max-prefix-limit {
        type max-prefix-limit;
      }
      container threshold-holder {
        leaf threshold {
          type max-prefix-threshold;
        }
        leaf teardown {
          type empty;
        }
      }
    }
    container default-originate {
      leaf default-originate-status {
        type empty;
      }
    }
    container prefix-list {
      description
        "either prefix list or distribution-list";
      container direction-in {
        leaf prefix-list-direction-in-prefix-name {
          type nei-prefix-list-filter;
        }
        leaf prefix-list-direction-in {
          type empty;
        }
      }
      container direction-out {
        leaf prefix-list-direction-out-prefix-name {
          type nei-prefix-list-filter;
        }
        leaf prefix-list-direction-out {
          type empty;
        }
      }
    }
    container neighbor-route-map {
      container neighbor-route-map-direction-in {
        leaf neighbor-route-map-name-direction-in {
          type common-def:name-string64;
        }
      }
      container neighbor-route-map-direction-out {
        leaf neighbor-route-map-name-direction-out {
          type common-def:name-string64;
        }
      }
    }
    leaf route-reflector-client {
      type empty;
    }
    container unsuppress-map {
      leaf map-name {
        type rmap-type;
      }
    }
    leaf af-nei-weight {
      type nei-weight;
    }
  }

  grouping bfd-config {
    leaf holdover-interval {
      type bfd:bfd-holdover-interval;
    }
    uses bfd:bfd-interval;
  }

  grouping router-bgp-neighbor-attributes {
    leaf description {
      type neighbor-description;
    }
    container local-as {
      leaf local-as-value {
        type local-as-num;
      }
      leaf no-prepend {
        type empty;
      }
    }
    container next-hop-self {
      choice ch-next-hop-self-type {
        case ca-next-hop-self-always {
          leaf next-hop-self-always {
            type empty;
          }
        }
        case ca-next-hop-self-status {
          leaf next-hop-self-status {
            type empty;
          }
        }
      }
    }
    container advertisement-interval {
      leaf value {
        type adv-value;
      }
    }
    leaf ebgp-btsh {
      type empty;
    }
    container ebgp-multihop {
      choice ch-ebgp-multihop-type {
        default "ca-ebgp-multihop-flag";
        case ca-ebgp-multihop-flag {
          leaf ebgp-multihop-flag {
            type empty;
          }
        }
        case ca-ebgp-multihop-count {
          leaf ebgp-multihop-count {
            type uint32 {
              range "1..255";
            }
          }
        }
      }
    }
    leaf password {
      type bgp-password;
    }
    container enforce-first-as {
      leaf nei-enforce-first-as {
        type empty;
      }
      leaf nei-enforce-first-as-disable {
        type empty;
      }
    }
    container timers {
      leaf nei-keep-alive {
        type nei-keep-alive;
      }
      leaf nei-hold-time {
        type nei-hold-time;
      }
    }
    leaf remove-private-as {
      type empty;
    }
    leaf as-override {
      type empty;
    }
    container soft-reconfiguration {
      leaf inbound {
        type empty;
      }
    }
    leaf static-network-edge {
      type empty;
    }
    container bfd {
      leaf bfd-enable {
        type empty;
      }
      uses bfd-config;
    }
  }

  grouping router-bgp-neighbor-cmds {
    container neighbor {
      container peer-grps {
        list neighbor-peer-grp {
          key "router-bgp-neighbor-peer-grp";
          leaf router-bgp-neighbor-peer-grp {
            type bgp-peergroup;
          }
          leaf peer-group-name {
            type empty;
          }
          leaf remote-as {
            type bgp-remote-as;
          }
          container update-source {
            choice ch-update-source {
              case ca-ipv4 {
                leaf sip-ipv4-address {
                  type sip-ipv4-address;
                }
              }
              case ca-eth {
                container ethernet-interface {
                  leaf interface-type {
                    type enumeration {
                      enum "ethernet" {
                        value 1;
                      }
                    }
                  }
                  leaf interface-name {
                    type update-source-ethernet-type;
                  }
                }
              }
              case ca-port-channel {
                leaf port-channel {
                  type interface:portchannel-type;
                }
              }
              case ca-loopback {
                leaf loopback {
                  type loopback-interface;
                }
              }
              case ca-ve {
                leaf ve-interface {
                  type interface:ve-type;
                }
              }
            }
          }
          uses router-bgp-neighbor-attributes;
          uses common-maxas-limit-group;
          container af-neighbor-capability {
            uses as4-capability-cmd;
          }
          container shutdown {
            leaf shutdown-status {
              type empty;
            }
            leaf generate-rib-out {
              type empty;
            }
          }
        }
      }
      container neighbor-ipv6s {
        list neighbor-ipv6-addr {
          key "router-bgp-neighbor-ipv6-address";
          leaf router-bgp-neighbor-ipv6-address {
            type inet:ipv6-address;
          }
          leaf remote-as {
            type bgp-remote-as;
          }
          leaf associate-peer-group {
            type bgp-peergroup;
          }
          container update-source {
            choice ch-update-source {
              case ca-ipv6 {
                leaf sip-ipv6-address {
                  type sip-ipv6-address;
                }
              }
              case ca-eth {
                container ethernet-interface {
                  leaf interface-type {
                    type enumeration {
                      enum "ethernet" {
                        value 1;
                      }
                    }
                  }
                  leaf interface-name {
                    type update-source-ethernet-type;
                  }
                }
              }
              case ca-port-channel {
                leaf port-channel {
                  type interface:portchannel-type;
                }
              }
              case ca-loopback {
                leaf loopback {
                  type loopback-interface;
                }
              }
              case ca-ve {
                leaf ve-interface {
                  type interface:ve-type;
                }
              }
            }
          }
          uses router-bgp-neighbor-attributes;
          uses common-maxas-limit-group;
          container af-neighbor-capability {
            uses as4-capability-cmd;
          }
          container shutdown {
            leaf shutdown-status {
              type empty;
            }
            leaf generate-rib-out {
              type empty;
            }
          }
        }
      }
      container neighbor-ips {
        list neighbor-addr {
          key "router-bgp-neighbor-address";
          leaf router-bgp-neighbor-address {
            type inet:ipv4-address;
          }
          leaf remote-as {
            type bgp-remote-as;
          }
          leaf associate-peer-group {
            type bgp-peergroup;
          }
          container update-source {
            choice ch-update-source {
              case ca-ipv4 {
                leaf sip-ipv4-address {
                  type sip-ipv4-address;
                }
              }
              case ca-eth {
                container ethernet-interface {
                  leaf interface-type {
                    type enumeration {
                      enum "ethernet" {
                        value 1;
                      }
                    }
                  }
                  leaf interface-name {
                    type update-source-ethernet-type;
                  }
                }
              }
              case ca-port-channel {
                leaf port-channel {
                  type interface:portchannel-type;
                }
              }
              case ca-loopback {
                leaf loopback {
                  type loopback-interface;
                }
              }
              case ca-ve {
                leaf ve-interface {
                  type interface:ve-type;
                }
              }
            }
          }
          uses router-bgp-neighbor-attributes;
          uses common-maxas-limit-group;
          container af-neighbor-capability {
            uses as4-capability-cmd;
          }
          container shutdown {
            leaf shutdown-status {
              type empty;
            }
            leaf generate-rib-out {
              type empty;
            }
          }
        }
      }
    }
  }

  grouping af-redistrubute-vrf-grouping {
    container redistribute {
      container bgp {
        leaf redistribute-bgp {
          type empty;
        }
        leaf bgp-metric {
          type conn-metric;
        }
        leaf bgp-route-map {
          type rmap-type;
        }
      }
      container connected {
        leaf redistribute-connected {
          type empty;
        }
        leaf unicast-metric {
          type conn-metric;
        }
        leaf redistribute-route-map {
          type rmap-type;
        }
      }
      container ospf {
        leaf redistribute-ospf {
          type empty;
        }
        container match {
          leaf ospf-internal {
            type empty;
          }
          leaf ospf-external1 {
            type empty;
          }
          leaf ospf-external2 {
            type empty;
          }
        }
        leaf ospf-metric {
          type conn-metric;
        }
        leaf ospf-route-map {
          type rmap-type;
        }
      }
      container static {
        leaf redistribute-static {
          type empty;
        }
        leaf unicast-static-metric {
          type conn-metric;
        }
        leaf static-route-map {
          type rmap-type;
        }
      }
    }
  }

  grouping af-redistrubute-unicast-grouping {
    container redistribute {
      container bgp {
        leaf redistribute-bgp {
          type empty;
        }
        leaf bgp-metric {
          type conn-metric;
        }
        leaf bgp-route-map {
          type rmap-type;
        }
      }
      container connected {
        leaf redistribute-connected {
          type empty;
        }
        leaf unicast-metric {
          type conn-metric;
        }
        leaf redistribute-route-map {
          type rmap-type;
        }
      }
      container ospf {
        leaf redistribute-ospf {
          type empty;
        }
        container match {
          leaf ospf-internal {
            type empty;
          }
          leaf ospf-external1 {
            type empty;
          }
          leaf ospf-external2 {
            type empty;
          }
        }
        leaf ospf-metric {
          type conn-metric;
        }
        leaf ospf-route-map {
          type rmap-type;
        }
      }
      container redistribute-isis {
        when "((/c:capabilities/c:bgp/c:redistribute-isis = \"true\"))";
        description
          "ISIS routes";
        presence "true";
        leaf redistribute-isis-route-map {
          description
            "Route map reference";
          type common-def:name-string63;
        }
        choice ch-isis-level {
          case ca-level-1 {
            leaf level-1 {
              description
                "Redistribution of IS-IS Level-1 routes only";
              type empty;
            }
          }
          case ca-level-2 {
            leaf level-2 {
              description
                "Redistribution of IS-IS Level-2 routes only";
              type empty;
            }
          }
          case ca-level-1-2 {
            leaf level-1-2 {
              description
                "Redistribution of IS-IS Level-1 and Level-2 routes";
              type empty;
            }
          }
        }
        leaf redistribute-isis-metric {
          type conn-metric;
        }
      }
      container static {
        leaf redistribute-static {
          type empty;
        }
        leaf unicast-static-metric {
          type conn-metric;
        }
        leaf static-route-map {
          type rmap-type;
        }
      }
    }
  }

  grouping af-aggregate-ipv6-address-cmd {
    list aggregate-ipv6-address {
      key "aggregate-ip-prefix";
      leaf aggregate-ip-prefix {
        type inet:ipv6-prefix;
      }
      uses common-aggregate-address-grouping;
    }
  }

  grouping af-aggregate-ipv4-address-cmd {
    list aggregate-address {
      key "aggregate-ip-prefix";
      leaf aggregate-ip-prefix {
        type inet:ipv4-prefix;
      }
      uses common-aggregate-address-grouping;
    }
  }

  grouping common-aggregate-address-grouping {
    leaf advertise-map {
      type advertise-map;
    }
    leaf as-set {
      type empty;
    }
    leaf attribute-map {
      type attribute-map;
    }
    leaf summary-only {
      type empty;
    }
    leaf suppress-map {
      type suppress-map;
    }
  }

  grouping common-multipath-grouping {
    container multipath {
      leaf multipath_ebgp {
        type empty;
      }
      leaf multipath_ibgp {
        type empty;
      }
      leaf multi-as {
        type empty;
      }
    }
  }

  grouping af-ipv4-uc-and-vrf-cmds {
    container af-ipv4-uc-and-vrf-cmds-call-point-holder {
      leaf bgp-redistribute-internal {
        type empty;
      }
      uses af-redistrubute-unicast-grouping;
    }
  }

  grouping af-ipv4-only-vrf-cmds {
    container af-ipv4-uc-and-vrf-cmds-call-point-holder {
      leaf bgp-redistribute-internal {
        type empty;
      }
      uses af-redistrubute-vrf-grouping;
    }
  }

  grouping af-ipv6-uc-and-vrf-cmds {
    container af-ipv6-uc-and-vrf-cmds-call-point-holder {
      leaf bgp-redistribute-internal {
        type empty;
      }
      uses af-redistrubute-unicast-grouping;
    }
  }

  grouping af-ipv6-only-vrf-cmds {
    container af-ipv6-uc-and-vrf-cmds-call-point-holder {
      leaf bgp-redistribute-internal {
        type empty;
      }
      uses af-redistrubute-vrf-grouping;
    }
  }

  grouping af-ipv6-uc-and-mc-cmds {
    uses af-ipv6-neighbor-cmds;
    container af-common-cmds-holder {
      uses af-common-cmds;
      uses graceful-restart-cmds;
    }
  }

  grouping af-ipv4-uc-and-mc-cmds {
    uses af-ipv4-neighbor-cmds;
    container af-common-cmds-holder {
      uses af-common-cmds;
      uses graceful-restart-cmds;
    }
  }

  grouping af-ipv6-uc-cmds {
    uses af-ipv6-uc-and-vrf-cmds;
    uses af-aggregate-ipv6-address-cmd;
    uses af-ipv6-network-cmds;
    uses af-ipv6-uc-and-mc-cmds;
    leaf ipv6-ucast-next-hop-recursion {
      type empty;
    }
  }

  grouping af-ipv6-uc-vrf-cmds {
    uses af-ipv6-only-vrf-cmds;
    uses af-aggregate-ipv6-address-cmd;
    uses af-ipv6-network-cmds;
    uses af-ipv6-vrf-neighbor-cmds;
    uses af-common-cmds;
  }

  grouping af-ipv4-uc-vrf-cmds {
    uses af-ipv4-only-vrf-cmds;
    list static-network {
      key "static-network-address";
      leaf static-network-address {
        type inet:ipv4-prefix;
      }
      leaf static-network-distance {
        type sdistance;
      }
    }
    uses af-aggregate-ipv4-address-cmd;
    uses af-ipv4-network-cmds;
    uses af-ipv4-vrf-neighbor-cmds;
    uses af-common-cmds;
  }

  grouping af-ipv4-uc-cmds {
    uses af-ipv4-uc-and-vrf-cmds;
    list static-network {
      key "static-network-address";
      leaf static-network-address {
        type inet:ipv4-prefix;
      }
      leaf static-network-distance {
        type sdistance;
      }
    }
    uses af-aggregate-ipv4-address-cmd;
    uses af-ipv4-network-cmds;
    uses af-ipv4-uc-and-mc-cmds;
    leaf next-hop-recursion {
      type empty;
    }
    container next-hop-mpls {
      when "((/c:capabilities/c:bgp/c:next-hop-mpls = \"true\"))";
      presence "true";
      choice ch-compare-lsp-follow-igp {
        case ca-compare-lsp-metric {
          leaf compare-lsp-metric {
            type empty;
          }
        }
        case ca-follow-igp {
          leaf follow-igp {
            type empty;
          }
        }
      }
    }
  }

  grouping af-basic-cmds {
    uses common-maximum-paths-grouping;
    uses common-multipath-grouping;
    leaf always-propagate {
      type empty;
    }
    leaf default-information-originate {
      type empty;
    }
    leaf rib-route-limit {
      type rib-route-number;
    }
  }

  grouping af-common-cmds {
    uses af-basic-cmds;
    leaf client-to-client-reflection {
      type empty;
    }
    container dampening {
      choice ch-dampening-source {
        default "ca-dampening-flag";
        case ca-dampening-flag {
          leaf dampening-flag {
            type empty;
            description
              "This Flag is to indicate dampening feature  is enabled";
          }
        }
        case ca-dampening-specify-values {
          container values {
            leaf half-time {
              type htime;
            }
            leaf reuse-value {
              type damp-reuse-value;
            }
            leaf start-suppress-time {
              type damp-start-suppress-value;
            }
            leaf max-suppress-time {
              type damp-max-suppress-value;
            }
          }
        }
        case ca-dampening-route-map {
          leaf dampening-route-map {
            type rmap-type;
          }
        }
      }
    }
    leaf default-metric {
      type default-metric-number;
    }
    leaf next-hop-enable-default {
      type empty;
    }
    container table-map {
      leaf table-map-route-map {
        type rmap-type;
      }
    }
    leaf update-time {
      type update-time-type;
    }
  }

  grouping graceful-restart-cmds {
    container graceful-restart {
      leaf graceful-restart-status {
        type empty;
      }
    }
  }

  grouping bgp-cmds {
    container router-bgp {
      presence "true";
      uses router-bgp-cmds;
      uses address-family-group;
    }
  }

  grouping router-bgp-cmds {
    container router-bgp-attributes {
      leaf local-as {
        type local-as-type;
      }
      leaf always-compare-med {
        type empty;
      }
      leaf compare-med-empty-aspath {
        type empty;
      }
      leaf med-missing-as-worst {
        type empty;
      }
      leaf as-path-ignore {
        type empty;
      }
      leaf compare-routerid {
        type empty;
      }
      leaf install-igp-cost {
        type empty;
      }
      container cluster-id {
        choice ch-cluster-id {
          case ca-cluster-id {
            leaf cluster-id-value {
              type decimal-number;
            }
          }
          case ca-cluster-id-ipv4-address {
            leaf cluster-id-ipv4-address {
              type inet:ipv4-address;
            }
          }
        }
      }
      leaf default-local-preference {
        type local-preference-number;
      }
      container distance {
        leaf ext-route-distance {
          type ext-route-distance;
        }
        leaf int-route-distance {
          type int-route-distance;
        }
        leaf lcl-route-distance {
          type lcl-route-distance;
        }
      }
      container capability {
        leaf as4-enable {
          type empty;
        }
      }
      container maxas-limit {
        container in {
          leaf num-as-in-path {
            type num-as-in-path;
          }
        }
      }
      leaf enforce-first-as {
        type empty;
      }
      leaf fast-external-fallover {
        type empty;
      }
      container timers {
        leaf keep-alive {
          type nei-keep-alive;
        }
        leaf hold-time {
          type nei-hold-time;
        }
      }
      leaf log-dampening-debug {
        type empty;
      }
      container confederation {
        leaf identifier {
          type cidentifier;
        }
        leaf-list peers {
          type cidentifier;
        }
      }
      container bfd {
        uses bfd-config;
      }
      leaf auto-shutdown-new-neighbors {
        description
          "Auto shutdown new neighbor";
        type empty;
      }
      uses router-bgp-neighbor-cmds;
    }
  }

  grouping route-target-import {
    list import {
      key "target-community";
      leaf target-community {
        type rd-rt-type;
        description
          "Target VPN Extended Community";
      }
    }
  }

  grouping route-target-export {
    list export {
      key "target-community";
      leaf target-community {
        type rd-rt-type;
        description
          "Target VPN Extended Community";
      }
    }
  }

  grouping route-target-both {
    list both {
      key "target-community";
      leaf target-community {
        type rd-rt-type;
        description
          "Target VPN Extended Community";
      }
    }
  }

  grouping evpn-instance-config {
    container route-target {
      list both {
        key "target-community";
        leaf target-community {
          type rt-type;
          description
            "Target VPN Extended Community";
        }
        leaf ignore-as {
          type empty;
        }
      }
      list export {
        key "target-community";
        leaf target-community {
          type rt-type;
          description
            "Target VPN Extended Community";
        }
      }
      list import {
        key "target-community";
        leaf target-community {
          type rt-type;
          description
            "Target VPN Extended Community";
        }
        leaf ignore-as {
          type empty;
        }
      }
    }
    container route-distinguisher {
      choice ch-rd-type {
        case ca-rd-auto {
          leaf auto {
            type empty;
          }
        }
      }
    }
    leaf df-delay-timer {
      description
        "DF delay timer";
      type delay-timer;
    }
    container duplicate-mac-timer {
      description
        "Duplicate mac timer";
      leaf duplicate-mac-timer-value {
        type dup-mac-timer;
      }
      leaf max-count {
        type max-count;
        description
          "Max count.";
      }
    }
    container bridge-domain {
      container bd-add {
        leaf bd-range-add {
          description
            "Add bridge domains to the EVPN Instance.";
          type tunnels:bridge-domain-id-range-type;
        }
        leaf bd-range-remove {
          description
            "Remove bridge domains to the EVPN Instance.";
          type tunnels:bridge-domain-id-range-type;
        }
      }
      list evpn-bd {
        description
          "EVPN instance bridge domain config";
        key "bd-number";
        leaf bd-number {
          type bridge-domain:bridge-domain-id-type;
        }
        leaf rd {
          type rd-type;
        }
        container route-target {
          uses route-target-import;
          uses route-target-export;
          uses route-target-both;
        }
      }
    }
    container vlan {
      container vlan-add {
        leaf add {
          description
            "Add VLANS to the EVPN Instance.";
          type interface:ui32-vlan-range;
        }
        leaf remove {
          description
            "Remove VLANS to the EVPN Instance.";
          type interface:ui32-vlan-range;
        }
      }
      list evpn-vlan {
        description
          "EVPN instance config";
        key "vlan-number";
        leaf vlan-number {
          type interface:vlan-type;
        }
        leaf rd {
          type rd-type;
        }
        container route-target {
          uses route-target-import;
          uses route-target-export;
          uses route-target-both;
        }
      }
    }
  }

  augment "/common-def:routing-system" {
    container evpn-config {
      container evpn {
        list evpn-instance {
          description
            "EVPN instance config";
          key "instance-name";
          leaf instance-name {
            type evpn-type;
          }
          uses evpn-instance-config;
        }
      }
    }
  }
  augment "/common-def:routing-system/common-def:router" {
    uses bgp-cmds;
  }
}
