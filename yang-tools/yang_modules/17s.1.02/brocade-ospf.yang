/*********************************************************************
 * Copyright (c) 2010 by Brocade Communications Systems, Inc.
 * All rights reserved.
 * brocade-ospf.yang: Brocade OSPF data model
 *
 * Nov 2010, bvreddy
 *
 *
 ********************************************************************/
module brocade-ospf {
  namespace "urn:brocade.com:mgmt:brocade-ospf";
  prefix ospf;

  import brocade-interface {
    prefix interface;
  }
  import brocade-ip-config {
    prefix ip-config;
  }
  import brocade-common-def {
    prefix common-def;
  }
  import brocade-intf-loopback {
    prefix intf-loopback;
  }
  import ietf-inet-types {
    prefix inet;
  }

  organization "Brocade Communications Systems, Inc.";
  contact
    "Brocade Communications Systems, Inc.
     Postal: 130 Holger Way,
             San Jose, CA 95134 
              U.S.A
     Tel: +1-408-333-8000
     E-mail: support@Brocade.com 
     web: www.brocade.com.";
  description
    "This management module is an instrumentation to manage 
     OSPF Version 2 Protocol.";

  revision 2010-11-29 {
    description
      "Initial version of this management module.";
  }

  typedef ospf-area-id {
    type string {
      pattern "((([0-9]|[1-9][0-9]|1[0-9][0-9]|2[0-4][0-9]|25[0-5])\\.)(([0-9]|[1-9][0-9]|1[0-9][0-9]|2[0-4][0-9]|25[0-5])\\.){2}([0-9]|[1-9][0-9]|1[0-9][0-9]|2[0-4][0-9]|25[0-5]))|(([0-9])|([1-9]([0-9]{1,8}))|([1]([0-9]{1,9}))|([2][0]([0-9]{1,8}))|([2][1][0-3]([0-9]{1,7}))|([2][1][4][0-6]([0-9]{1,6}))|([2][1][4][7][0-3]([0-9]{1,5}))|([2][1][4][7][4][0-7]([0-9]{1,4}))|([2][1][4][7][4][8][0-2]([0-9]{1,3}))|([2][1][4][7][4][8][3][0-5]([0-9]{1,2}))|([2][1][4][7][4][8][3][6][0-3][0-9])|([2][1][4][7][4][8][3][6][4][0-7]))";
    }
  }

  typedef ospf-auth-psswd-string {
    type string;
  }

  typedef big-metric {
    type uint32;
  }

  typedef range-metric {
    type uint32;
  }

  typedef band-width {
    type uint32 {
      range "1..4294967";
    }
    units "megabits per second";
  }

  typedef metric-type {
    type enumeration {
      enum "type1" {
        value 1;
      }
      enum "type2" {
        value 2;
      }
    }
  }

  typedef route-type-enum {
    type enumeration {
      enum "external" {
        value 1;
      }
      enum "inter-area" {
        value 2;
      }
      enum "intra-area" {
        value 3;
      }
      enum "route-map" {
        value 4;
      }
    }
  }

  typedef ospf-ipv4-address {
    type inet:ipv4-address;
  }

  typedef ipv4-prefix-name-t {
    type common-def:name-string32;
    description
      "Word:1-32;;IP prefix-list name";
  }

  grouping common-link-props {
    container authentication-key {
      container no-encrypt-auth-key-table {
        leaf no-encrypt-auth-key {
          type ospf-auth-psswd-string;
        }
      }
    }
    leaf hello-interval {
      default "10";
      type common-def:time-interval-sec {
        range "1..65535";
      }
    }
    leaf dead-interval {
      default "40";
      type common-def:time-interval-sec {
        range "3..65535";
      }
    }
    leaf retransmit-interval {
      type common-def:time-interval-sec {
        range "0..3600";
      }
    }
    leaf transmit-delay {
      type common-def:time-interval-sec {
        range "0..3600";
      }
    }
    container md5-authentication {
      leaf key-activation-wait-time {
        type common-def:time-interval-sec {
          range "0..14400";
        }
      }
      container key-table {
        leaf key-id {
          type uint32 {
            range "1..255";
          }
        }
        leaf md5-authentication-key {
          type ospf-auth-psswd-string;
        }
      }
    }
  }

  grouping interface-eth-ospf {
    container interface-eth-ospf-conf {
      uses interface-ospf;
    }
  }

  grouping interface-vlan-ospf {
    container interface-vlan-ospf-conf {
      uses interface-ospf;
    }
  }

  grouping interface-loopback-ospf {
    container interface-loopback-ospf-conf {
      uses interface-ospf;
    }
  }

  typedef database-filter-options {
    type enumeration {
      enum "allow-default-out" {
        value 1;
      }
      enum "allow-default-and-type4-out" {
        value 2;
      }
      enum "out" {
        value 3;
      }
    }
  }

  grouping interface-ospf {
    container ospf1 {
      leaf area {
        type ospf-area-id;
      }
      leaf auth-change-wait-time {
        type common-def:time-interval-sec {
          range "0..14400";
        }
      }
      uses common-link-props;
      leaf cost {
        type uint32 {
          range "1..65535";
        }
      }
      leaf network {
        type enumeration {
          enum "broadcast" {
            value 1;
          }
          enum "non-broadcast" {
            value 2;
          }
          enum "point-to-point" {
            value 3;
          }
        }
      }
      container database-filter {
        leaf all-out {
          type empty;
        }
        leaf all-external {
          type database-filter-options;
        }
        leaf all-summary-external {
          type database-filter-options;
        }
      }
      leaf mtu-ignore {
        type empty;
      }
      leaf active {
        type empty;
      }
      leaf passive {
        type empty;
      }
      leaf priority {
        type uint32 {
          range "0..255";
        }
      }
      container bfd {
        description
          "Set Bidirectional Forwarding Detection operation mode on this interface";
        leaf intf-bfd-enable {
          type empty;
          description
            "Enable bfd on this interface";
        }
      }
    }
  }

  grouping global-ospf {
    leaf database-overflow-interval {
      type common-def:time-interval-sec {
        range "0..86400";
      }
    }
    container default-information-originate {
      presence "true";
      leaf always {
        type empty;
      }
      leaf def-orig-metric {
        type uint32 {
          range "1..65535";
        }
      }
      leaf def-orig-metric-type {
        type metric-type;
      }
      leaf def-orig-route-map {
        default "";
        type string;
      }
    }
    leaf default-passive-interface {
      type empty;
    }
    leaf default-metric {
      type uint32 {
        range "1..65535";
      }
      default "10";
    }
    leaf external-lsdb-limit {
      type uint32 {
        range "1..14913080";
      }
      default "14913080";
    }
    container log {
      container adjacency {
        presence "true";
        leaf dr-only {
          type empty;
        }
      }
      leaf log-all {
        type empty;
      }
      container bad-packet {
        presence "true";
        leaf log-checksum {
          type empty;
        }
      }
      leaf log-database {
        type empty;
      }
      leaf log-retransmit {
        type empty;
      }
    }
    leaf ospf-metric-type {
      type metric-type;
    }
    list neighbor {
      key "neighbor-addr";
      leaf neighbor-addr {
        type ospf-ipv4-address;
      }
    }
    container redistribute {
      container connected {
        presence "true";
        leaf connected-route-map {
          type common-def:name-string63;
        }
      }
      container static {
        presence "true";
        leaf static-route-map {
          type common-def:name-string63;
        }
      }
      container bgp {
        presence "true";
        leaf bgp-route-map {
          type common-def:name-string63;
        }
      }
      container redistribute-ospf {
        presence "true";
        leaf ospf-route-map {
          type common-def:name-string63;
        }
      }
    }
    container rfc1583-compatibility {
      presence "rfc1583";
      leaf rfc1583-compatibility-flag {
        type empty;
      }
    }
    list area {
      key "area-id";
      leaf area-id {
        type ospf-area-id;
      }
      leaf normal {
        type empty;
      }
      container nssa {
        container metric {
          leaf nssa-value {
            type big-metric;
          }
          leaf no-summary1 {
            type empty;
          }
        }
        leaf default-information-originate {
          type empty;
        }
      }
      container stub {
        container metric {
          leaf stub-value {
            type big-metric;
          }
          leaf no-summary {
            type empty;
          }
        }
      }
      list range {
        key "range-address range-mask";
        leaf range-address {
          type inet:ipv4-address;
          mandatory true;
        }
        leaf range-mask {
          type inet:ipv4-address;
          mandatory true;
        }
        leaf range-effect {
          type enumeration {
            enum "advertise" {
              value 1;
            }
            enum "not-advertise" {
              value 2;
            }
          }
        }
        leaf range-cost {
          type range-metric;
          default "0";
        }
      }
      container prefix-list {
        description
          "either prefix list or distribution-list";
        container direction-in {
          leaf prefix-list-direction-in-prefix-name {
            type ipv4-prefix-name-t;
          }
          leaf prefix-list-direction-in {
            type empty;
          }
        }
        container direction-out {
          leaf prefix-list-direction-out-prefix-name {
            type ipv4-prefix-name-t;
          }
          leaf prefix-list-direction-out {
            type empty;
          }
        }
      }
      list virtual-link {
        key "virt-link-neighbor";
        leaf virt-link-neighbor {
          type inet:ipv4-address;
        }
        uses common-link-props;
      }
    }
    container auto-cost {
      container reference-bandwidth {
        leaf ref-bandwidth {
          type band-width;
          default "100";
        }
        leaf use-active-ports {
          type empty;
        }
      }
    }
    list distance {
      key "route-type";
      leaf route-type {
        type route-type-enum;
      }
      leaf route-map-name {
        when "../route-type ='route-map' ";
        type common-def:name-string63;
      }
      leaf dist-value {
        mandatory true;
        type uint32 {
          range "1..255";
        }
      }
      leaf source-ip {
        when "../route-type ='route-map'";
        type ospf-ipv4-address;
      }
      leaf source-ip-mask {
        when "../route-type ='route-map'";
        type ospf-ipv4-address;
      }
    }
    container distribute-list {
      container route-map {
        leaf route-map {
          type common-def:name-string63;
        }
        leaf input {
          type empty;
        }
      }
    }
    container max-metric {
      container router-lsa {
        presence "true";
        leaf all-vrfs {
          type empty;
        }
        leaf all-lsas {
          type empty;
        }
        container external-lsa {
          presence "true";
          leaf external-lsa-val {
            type uint32 {
              range "1..16777214";
            }
            default "16711680";
          }
        }
        container summary-lsa {
          presence "true";
          leaf summary-lsa-val {
            type uint32 {
              range "1..16777214";
            }
            default "16711680";
          }
        }
        container link {
          leaf all {
            type empty;
          }
          leaf ptp {
            type empty;
          }
          leaf stub {
            type empty;
          }
          leaf transit {
            type empty;
          }
        }
        container on-startup {
          leaf time {
            type uint32 {
              range "5 ..86400";
            }
            units "seconds";
          }
          leaf wait-for-bgp {
            type empty;
          }
          leaf all-lsas-onstartup {
            type empty;
          }
          container external-lsa-onstartup {
            presence "true";
            leaf external-lsa-val-onstartup {
              type uint32 {
                range "1..16777214";
              }
              default "16711680";
            }
          }
          container summary-lsa-onstartup {
            presence "true";
            leaf summary-lsa-val-onstartup {
              type uint32 {
                range "1..16777214";
              }
              default "16711680";
            }
          }
          container link-onstartup {
            leaf all-link-onstartup {
              type empty;
            }
            leaf ptp-link-onstartup {
              type empty;
            }
            leaf stub-link-onstartup {
              type empty;
            }
            leaf transit-link-onstartup {
              type empty;
            }
          }
        }
      }
    }
    list summary-address {
      key "sum-address sum-address-mask";
      leaf sum-address {
        type ospf-ipv4-address;
      }
      leaf sum-address-mask {
        type inet:ipv4-address;
      }
    }
    container timers {
      leaf lsa-group-pacing {
        type common-def:time-interval-sec {
          range "10..1800";
        }
      }
      container throttle {
        container spf {
          leaf init-delay {
            type common-def:time-interval-msec {
              range "0..60000";
            }
          }
          leaf hold-time {
            type common-def:time-interval-msec {
              range "0..60000";
            }
          }
          leaf max-hold-time {
            type common-def:time-interval-msec {
              range "0..60000";
            }
          }
        }
      }
    }
    leaf vrf-lite-capability {
      type empty;
    }
    leaf maximum-paths {
      type uint8 {
        range "1..64";
      }
      description
        "The maximum number of paths to a destination.";
    }
    container global-bfd {
      description
        "Configure BFD for OSPFv2 on all OSPFv2 enabled interfaces";
      leaf bfd-enable {
        type empty;
      }
      leaf holdover-interval {
        type uint8 {
          range "0..20";
        }
        units "Seconds";
        description
          "Holdover-interval is the time by which the BFD session DOWN notification to OSPF is delayed.If within that holdover time, the BFD session is UP then OSPF is not notified of the BFD session flap";
      }
    }
  }

  augment "/common-def:routing-system/common-def:router" {
    list ospf {
      key "vrf";
      leaf vrf {
        type string {
          length "1..64";
        }
      }
      uses global-ospf;
    }
  }
  augment "/common-def:routing-system/interface:interface/interface:ve/ip-config:ip" {
    uses interface-vlan-ospf;
  }
  augment "/common-def:routing-system/interface:interface/intf-loopback:loopback/ip-config:ip" {
    uses interface-loopback-ospf;
  }
  augment "/interface:interface/interface:ethernet/interface:ip" {
    uses interface-eth-ospf;
  }
}
