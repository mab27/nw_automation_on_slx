/*********************************************************************
 * Copyright (c) 2015 by Brocade Communications Systems, Inc.
 * All rights reserved.
 * brocade-rbridge-lag.yang: Brocade LAG data model
 *
 *
 *
 ********************************************************************/
module brocade-rbridge-lag {
  namespace "urn:brocade.com:mgmt:brocade-rbridge-lag";
  prefix rbridge-lag;

  import brocade-vcs {
    prefix vcs;
  }

  organization "Brocade Communications Systems, Inc.";
  contact
    "Brocade Communications Systems, Inc.
     Postal: 130 Holger Way,
             San Jose, CA 95134
              U.S.A
     Tel: +1-408-333-8000
     E-mail: support@Brocade.com
     web: www.brocade.com.";
  description
    "This management module is an instrumentation to manage
     LAG protocol.";

  revision 2015-03-16 {
    description
      "Initial version of this management module.";
  }

  container load-balance {
    container hash {
      when "((/vcs:local-node/vcs:swbd-number != \"163\") and (/vcs:local-node/vcs:swbd-number != \"3000\") and (/vcs:local-node/vcs:swbd-number != \"3001\"))";
      container ethernet {
        leaf sa-mac {
          type empty;
        }
        leaf da-mac {
          type empty;
        }
        leaf vlan {
          type empty;
        }
        leaf etype {
          type empty;
        }
      }
      container ip {
        leaf src-l4-port {
          type empty;
        }
        leaf dst-l4-port {
          type empty;
        }
        leaf src-ip {
          type empty;
        }
        leaf dst-ip {
          type empty;
        }
        leaf protocol {
          type empty;
        }
      }
      container ipv6 {
        leaf ipv6-src-l4-port {
          type empty;
        }
        leaf ipv6-dst-l4-port {
          type empty;
        }
        leaf ipv6-src-ip {
          type empty;
        }
        leaf ipv6-dst-ip {
          type empty;
        }
        leaf ipv6-next-hdr {
          type empty;
        }
      }
      container mpls {
        leaf label1 {
          type empty;
        }
        leaf label2 {
          type empty;
        }
        leaf label3 {
          type empty;
        }
      }
    }
    container po-load-balance {
      leaf load-balance-type {
        type enumeration {
          enum "dst-mac-vid" {
            value 1;
          }
          enum "src-mac-vid" {
            value 2;
          }
          enum "src-dst-mac-vid" {
            value 3;
          }
          enum "src-dst-ip" {
            value 4;
          }
          enum "src-dst-ip-mac-vid" {
            value 5;
          }
          enum "src-dst-ip-port" {
            value 6;
          }
          enum "src-dst-ip-mac-vid-port" {
            value 7;
          }
        }
        default "src-dst-ip-mac-vid-port";
      }
    }
  }
  container lag {
    when "((/vcs:local-node/vcs:swbd-number != \"163\") and (/vcs:local-node/vcs:swbd-number != \"3000\") and (/vcs:local-node/vcs:swbd-number != \"3001\"))";
    container hash {
      container hdr-start {
        leaf fwd-term {
          type enumeration {
            enum "fwd" {
              value 1;
            }
            enum "term" {
              value 2;
            }
          }
        }
      }
      container bos {
        leaf start-skip {
          type enumeration {
            enum "start" {
              value 1;
            }
            enum "skip" {
              value 2;
            }
          }
        }
      }
      leaf hdr-count {
        type uint32 {
          range "1..3";
        }
      }
      leaf rotate {
        type uint32 {
          range "0..15";
        }
      }
      leaf normalize {
        type empty;
      }
      leaf srcport {
        type empty;
      }
      leaf pwctrlword {
        type empty;
      }
      container speculate-mpls {
        leaf enable-eth-ip {
          type enumeration {
            enum "enable" {
              value 1;
            }
            enum "inner-eth" {
              value 2;
            }
            enum "inner-ip-raw" {
              value 3;
            }
            enum "inner-ip-tag" {
              value 4;
            }
            enum "inner-ipv6-raw" {
              value 5;
            }
            enum "inner-ipv6-tag" {
              value 6;
            }
          }
        }
      }
    }
  }
}
