/*********************************************************************
 * Copyright (c) 2011 by Brocade Communications Systems, Inc.
 * All rights reserved.
 * brocade-xstp.yang: Brocade xSTP Data Model
 *
 * July 2011, Sudheendra Kulkarni, Sanjeev C Joshi 
 *
 *
 ********************************************************************/
module brocade-xstp {
  namespace "urn:brocade.com:mgmt:brocade-xstp";
  prefix xstp;

  import brocade-interface {
    prefix interface;
  }

  organization "Brocade Communications Systems, Inc.";
  contact
    "Brocade Communications Systems, Inc.
     Postal: 130 Holger Way
            San Jose, CA 95134
            U.S.A
     Tel: +1-408-333-8000
     E-mail: support@Brocade.com
     Web: www.brocade.com";
  description
    "This management module is an instrumentation to manage the 
     Spanning Tree Protocol (STP).          
             
     Glossary of the terms used:
     --------------------------- 
             
    ";

  revision 2011-07-05 {
    description
      "Initial version of this management module.";
  }

  typedef xstp-ui32-vlan-range {
    type string {
      pattern "(([1-9][0-9]{0,2})|([1-3][0-9]{3})|(40[0-8][0-9])|(4090))(-(([1-9][0-9]{0,2})|([1-3][0-9]{3})|(40[0-8][0-9])|(4090)))?((,(([1-9][0-9]{0,2})|([1-3][0-9]{3})|(40[0-8][0-9])|(4090))(-(([1-9][0-9]{0,2})|([1-3][0-9]{3})|(40[0-8][0-9])|(4090)))?)?)*" {
        description
          "The definition for specifying the vlan range.";
      }
    }
  }

  typedef mstp-instance-type {
    type uint8 {
      range "1..31" {
        error-message "% Error: Value out of range at '^' marker";
      }
    }
  }

  grouping xstp-config {
    uses xstp-timer-config-with-default;
    leaf description {
      type string {
        length "0..64";
      }
      default "";
    }
    leaf cluster-system-id {
      type uint8 {
        range "1..255";
      }
      description
        "Indicates the last byte of cluster system id.
         Normally a switch mac address is used to derive
         spanning tree system id or bridge id. For MCT
         cluster deployments a virtual system id is comupted
         as \"<3-byte-OUI>:<2-byte-cluster-id>:00\". In case
         of collistion, the last byte of virtual system id
         can be changed via this configuration.";
    }
    leaf bridge-priority {
      type uint32 {
        range "0..61440" {
          error-message "% Error: Value out of range at '^' marker";
        }
      }
      default "32768";
    }
    container error-disable-timeout {
      leaf enable {
        type empty;
      }
      leaf interval {
        type uint32 {
          range "10..1000000" {
            error-message "% Error: Value out of range at '^' marker";
          }
        }
        default "300";
      }
    }
    container port-channel {
      leaf path-cost {
        type enumeration {
          enum "custom";
          enum "standard";
        }
        default "standard";
      }
    }
    leaf shutdown {
      type empty;
    }
  }

  grouping pvst-config {
    uses xstp-config;
    list vlan {
      key "id";
      leaf id {
        type uint32 {
          range "1..4090" {
            error-message "% Error: Value out of range at '^' marker";
          }
        }
      }
      leaf priority {
        type uint32 {
          range "0..61440" {
            error-message "% Error: Value out of range at '^' marker";
          }
        }
      }
      uses xstp-timer-config;
    }
  }

  grouping xstp-timer-config-with-default {
    container timer-config {
      leaf hello-time {
        type uint32 {
          range "1..10" {
            error-message "% Error: Value out of range at '^' marker";
          }
        }
        default "2";
      }
      leaf forward-delay {
        type uint32 {
          range "4..30" {
            error-message "% Error: Value out of range at '^' marker";
          }
        }
        default "15";
      }
      leaf max-age {
        type uint32 {
          range "6..40" {
            error-message "% Error: Value out of range at '^' marker";
          }
        }
        default "20";
      }
    }
  }

  grouping xstp-timer-config {
    container timer-config {
      leaf hello-time {
        type uint32 {
          range "1..10" {
            error-message "% Error: Value out of range at '^' marker";
          }
        }
      }
      leaf forward-delay {
        type uint32 {
          range "4..30" {
            error-message "% Error: Value out of range at '^' marker";
          }
        }
      }
      leaf max-age {
        type uint32 {
          range "6..40" {
            error-message "% Error: Value out of range at '^' marker";
          }
        }
      }
    }
  }

  grouping port-inst-xstp-config {
    leaf cost {
      type uint32 {
        range "1..200000000" {
          error-message "% Error: Value out of range at '^' marker";
        }
      }
    }
    leaf priority {
      type uint32 {
        range "0..240" {
          error-message "% Error: Value out of range at '^' marker";
        }
      }
      default "128";
    }
    leaf restricted-role {
      type empty;
    }
    leaf restricted-tcn {
      type empty;
    }
  }

  grouping port-xstp-config {
    leaf autoedge {
      type empty;
    }
    leaf cost {
      type uint32 {
        range "1..200000000";
      }
    }
    container portfast {
      leaf portfastbasic {
        type empty;
      }
      leaf bpdu-guard {
        type empty;
      }
    }
    container edgeport {
      leaf edgeportbasic {
        type empty;
      }
      leaf bpdu-guard {
        type empty;
      }
    }
    container guard {
      leaf root {
        type empty;
      }
    }
    leaf bpdu-mac {
      type enumeration {
        enum "0100.0ccc.cccd" {
          value 1;
        }
      }
    }
    leaf link-type {
      type enumeration {
        enum "point-to-point";
        enum "shared";
      }
    }
    leaf priority {
      type uint32 {
        range "0..240" {
          error-message "% Error: Value out of range at '^' marker";
        }
      }
    }
    leaf restricted-role {
      type empty;
    }
    leaf restricted-tcn {
      type empty;
    }
    leaf shutdown {
      type empty;
    }
  }

  augment "/interface:protocol" {
    container spanning-tree {
      container stp {
        presence "true";
        uses xstp-config;
      }
      container rstp {
        presence "true";
        uses xstp-config;
        leaf transmit-holdcount {
          type uint32 {
            range "1..10" {
              error-message
                "% Error: Value out of range at '^'
                 marker";
            }
          }
          default "6";
        }
      }
      container pvst {
        presence "true";
        uses pvst-config;
      }
      container rpvst {
        presence "true";
        uses pvst-config;
        leaf transmit-holdcount {
          type uint32 {
            range "1..10" {
              error-message
                "% Error: Value out of range at '^'
                 marker";
            }
          }
          default "6";
        }
      }
      container mstp {
        presence "true";
        uses xstp-config;
        leaf cisco-interoperability {
          type enumeration {
            enum "enable";
            enum "disable";
          }
          default "disable";
        }
        list instance {
          key "id";
          leaf id {
            type mstp-instance-type;
          }
          leaf vlan {
            type xstp-ui32-vlan-range;
          }
          leaf priority {
            type uint32 {
              range "0..61440" {
                error-message
                  "% Error: Value out of range at
                    '^' marker";
              }
            }
          }
        }
        leaf region {
          type string {
            length "0..32";
          }
          default "";
        }
        leaf revision {
          type uint16 {
            range "0..255" {
              error-message
                "% Error: Value out of range at 
                 '^' marker";
            }
          }
          default "0";
        }
        leaf max-hops {
          type uint32 {
            range "1..40" {
              error-message
                "% Error: Value out of range at '^'
                 marker";
            }
          }
          default "20";
        }
        leaf transmit-holdcount {
          type uint32 {
            range "1..10" {
              error-message
                "% Error: Value out of range at '^'
                 marker";
            }
          }
          default "6";
        }
      }
    }
  }
  augment "/interface:interface/interface:ethernet" {
    container spanning-tree {
      uses port-xstp-config;
      list vlan {
        key "id";
        leaf id {
          type uint32 {
            range "1..4090" {
              error-message "VLAN number out of range";
            }
          }
        }
        leaf cost {
          type uint32 {
            range "1..200000000" {
              error-message
                "% Error: Value out of range at '^' 
                 marker";
            }
          }
        }
        leaf priority {
          type uint32 {
            range "0..240" {
              error-message
                "% Error: Value out of range at '^' 
                 marker";
            }
          }
        }
        container guard {
          leaf root {
            type empty;
          }
        }
      }
      list instance {
        key "id";
        leaf id {
          type mstp-instance-type;
        }
        uses port-inst-xstp-config;
      }
    }
  }
  augment "/interface:interface/interface:port-channel" {
    container spanning-tree {
      uses port-xstp-config;
      list vlan {
        key "id";
        leaf id {
          type uint32 {
            range "1..4090" {
              error-message
                "% Error: Value out of range at '^' 
                 marker";
            }
          }
        }
        leaf cost {
          type uint32 {
            range "1..200000000" {
              error-message
                "% Error: Value out of range at '^' 
                 marker";
            }
          }
        }
        leaf priority {
          type uint32 {
            range "0..240" {
              error-message
                "% Error: Value out of range at '^' 
                 marker";
            }
          }
        }
        container guard {
          leaf root {
            type empty;
          }
        }
      }
      list instance {
        key "id";
        leaf id {
          type mstp-instance-type;
        }
        uses port-inst-xstp-config;
      }
    }
  }
  augment "/interface:interface-vlan/interface:vlan" {
    container spanning-tree {
      leaf stp-shutdown {
        type empty;
      }
    }
  }
}
