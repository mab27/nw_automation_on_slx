/*********************************************************************
 * Copyright (c) 2011 by Brocade Communications Systems, Inc.
 * All rights reserved.
 * brocade-ras-ext: Brocade  Data Model
 *
 * April 2011, Arun Kumar Viswanathan 
 *
 *
 ********************************************************************/
module brocade-ras-ext {
  namespace "urn:brocade.com:mgmt:brocade-ras-ext";
  prefix ras-extensions;

  import tailf-common {
    prefix tailf;
  }
  import ietf-yang-types {
    prefix ietfyang;
  }
  import tailf-xsd-types {
    prefix xs;
  }
  import brocade-common-def {
    prefix common-def;
  }

  organization "Brocade Communications Systems, Inc.";
  contact
    "Brocade Communications Systems, Inc.
     Postal: 130 Holger Way
             San Jose, CA 95134
             U.S.A
     Tel: +1-408-333-6061
     E-mail: support@Brocade.com
     web: www.brocade.com.";
  description
    "This module defines RASLOG related information.
     Copyright (c) 2010-11 by Brocade Communications Systems, Inc.
     All rights reserved.";
  reference "brocade-ras.yang";

  revision 2011-01-20 {
    description
      "Added new Action Point for RASLOG for Netconf interface.";
    reference "RAS.yang";
  }

  typedef switchid-type {
    type string {
      length "1..3" {
        error-message "Invalid rbridge-id (must be in the range 1 - 239) or all";
      }
    }
  }

  typedef ha-recovery-type {
    type enumeration {
      enum "unknown" {
        value 0;
      }
      enum "warm-recovery-in-progress" {
        value 1;
      }
      enum "cold-recovery-in-progress" {
        value 2;
      }
      enum "warm-recovered" {
        value 3;
      }
      enum "cold-recovered" {
        value 4;
      }
    }
  }

  typedef fru-type {
    type enumeration {
      enum "other" {
        value 1;
      }
      enum "unknown" {
        value 2;
      }
      enum "chassis" {
        value 3;
      }
      enum "cp" {
        value 4;
      }
      enum "other-cp" {
        value 5;
      }
      enum "switch-blade" {
        value 6;
      }
      enum "wwn" {
        value 7;
      }
      enum "power-suppy" {
        value 8;
      }
      enum "fan" {
        value 9;
      }
      enum "core-blade" {
        value 10;
      }
      enum "application-blade" {
        value 11;
      }
    }
  }

  typedef fru-operational-status {
    type enumeration {
      enum "other" {
        value 1;
      }
      enum "unknown" {
        value 2;
      }
      enum "on" {
        value 3;
      }
      enum "off" {
        value 4;
      }
      enum "faulty" {
        value 5;
      }
      enum "inserted" {
        value 6;
      }
      enum "ready" {
        value 7;
      }
      enum "up" {
        value 8;
      }
    }
  }

  typedef sensor-type {
    type enumeration {
      enum "unknown" {
        value 1;
      }
      enum "other" {
        value 2;
      }
      enum "temperature" {
        value 3;
      }
      enum "pressure" {
        value 4;
      }
      enum "emf" {
        value 5;
      }
      enum "current" {
        value 6;
      }
      enum "airflow" {
        value 7;
      }
      enum "frequency" {
        value 8;
      }
      enum "power" {
        value 9;
      }
      enum "door" {
        value 10;
      }
    }
  }

  typedef sensor-status {
    type enumeration {
      enum "unknown" {
        value 1;
      }
      enum "other" {
        value 2;
      }
      enum "ok" {
        value 3;
      }
      enum "warning" {
        value 4;
      }
      enum "failed" {
        value 5;
      }
    }
  }

  augment "/common-def:show" {
    container support {
      tailf:action "support" {
        input;
        output;
      }
    }
    container copy-support {
      tailf:action "status" {
        input;
        output;
      }
      tailf:action "group-list" {
        output;
      }
    }
    container infra-inventory {
      tailf:action "inventory" {
        input {
          choice opt {
            leaf chassis {
              type empty;
              mandatory false;
            }
            leaf fan {
              type empty;
              mandatory false;
            }
            leaf module {
              type empty;
              mandatory false;
            }
            leaf powerSupply {
              type empty;
              mandatory false;
            }
          }
        }
        output;
      }
    }
    container infra {
      description
        "Show system info";
      tailf:action "chassis" {
        input;
        output {
          list chassis-info {
            key "rbridge-id";
            leaf rbridge-id {
              type switchid-type;
              mandatory true;
            }
            leaf switch-type {
              type uint32;
              mandatory true;
            }
            leaf vendor {
              type string;
              mandatory true;
            }
            leaf vendor-version {
              type string;
              mandatory true;
            }
            leaf supplier-serial-number {
              type string;
              mandatory false;
            }
            leaf chassis-service-tag {
              type string;
              mandatory false;
            }
            leaf bay-id {
              type string;
              mandatory false;
            }
            leaf vendor-part-number {
              type string;
              mandatory false;
            }
            leaf brocade-part-number {
              type string;
              mandatory false;
            }
            leaf max-port {
              type int32;
              mandatory false;
            }
            leaf is-ha-enabled {
              type boolean;
              mandatory false;
            }
            leaf is-ha-redundant {
              type boolean;
              mandatory false;
            }
            leaf is-ha-heartbeat-up {
              type boolean;
              mandatory false;
            }
            leaf is-ha-synchronized {
              type boolean;
              mandatory false;
            }
            leaf ha-recovery {
              type ha-recovery-type;
              mandatory false;
            }
            list fru {
              leaf tag {
                type uint32;
                mandatory true;
              }
              leaf part-number {
                type string;
                mandatory true;
              }
              leaf serial-number {
                type string;
                mandatory true;
              }
              leaf field-replacable {
                type boolean;
                mandatory true;
              }
              leaf slot-number {
                type uint32;
                mandatory true;
              }
              leaf logical-slot-number {
                type uint32;
                mandatory false;
              }
              leaf blade-type-id {
                type uint32;
                mandatory false;
              }
              leaf slot-eth-port-cnt {
                type uint32;
                mandatory false;
              }
              leaf manufacturer-date {
                type xs:date;
                mandatory true;
              }
              leaf update-date {
                type xs:date;
                mandatory true;
              }
              leaf version {
                type string;
                mandatory true;
              }
              leaf vendor-equipment-type {
                type fru-type;
                mandatory true;
              }
              leaf operational-status {
                type fru-operational-status;
                mandatory true;
              }
              leaf manufacturer {
                type string;
                mandatory true;
              }
              leaf vendor {
                type string;
                mandatory false;
              }
              leaf vendor-part-number {
                type string;
                mandatory false;
              }
              leaf vendor-serial-number {
                type string;
                mandatory false;
              }
            }
          }
        }
      }
      container process {
        tailf:action "info" {
          input;
          output;
        }
        tailf:action "memory" {
          input {
            leaf summary {
              type empty;
              mandatory false;
            }
          }
          output;
        }
        tailf:action "cpu" {
          input {
            leaf summary {
              type empty;
              mandatory false;
            }
            leaf history {
              type empty;
              mandatory false;
            }
            leaf top {
              type empty;
              mandatory false;
            }
            leaf all-partitions {
              type empty;
              mandatory false;
            }
          }
          output;
        }
      }
      container environment {
        tailf:action "fan" {
          input;
          output;
        }
        tailf:action "power" {
          input;
          output;
        }
        tailf:action "temp" {
          input;
          output;
        }
        tailf:action "sensor" {
          input;
          output {
            list sensor-info {
              key "rbridge-id";
              leaf rbridge-id {
                type switchid-type;
                mandatory true;
              }
              list sensor {
                leaf id {
                  type uint32;
                  mandatory true;
                }
                leaf type {
                  type sensor-type;
                  mandatory true;
                }
                leaf sub-type {
                  type uint32;
                  mandatory true;
                }
                leaf status {
                  type sensor-status;
                  mandatory true;
                }
                leaf current-reading {
                  type int32;
                  mandatory true;
                }
              }
            }
          }
        }
        tailf:action "history" {
          input;
          output;
        }
      }
    }
    container logging {
      tailf:action "raslog" {
        input {
          leaf reverse {
            type empty;
            mandatory false;
          }
          leaf message-type {
            type enumeration {
              enum "SYSTEM" {
                value 0;
              }
              enum "DCE" {
                value 1;
              }
            }
            mandatory false;
          }
          leaf attribute {
            type enumeration {
              enum "FFDC" {
                value 3;
              }
            }
            mandatory false;
          }
          leaf blade {
            type string {
              length "3";
              pattern "MM1|MM2|LC1|LC2|LC3|LC4||LC5|LC6|LC7|LC8" {
                error-message "Invalid Blade Type, must be < MM[1-2] / LC[1-8] >";
              }
            }
            mandatory false;
          }
          leaf count {
            type uint16 {
              range "1..8192" {
                error-message "Invalid count (must be in the range 1 - 8192)";
              }
            }
            mandatory false;
          }
          leaf severity {
            type enumeration {
              enum "critical" {
                value 1;
              }
              enum "error" {
                value 2;
              }
              enum "warning" {
                value 3;
              }
              enum "info" {
                value 4;
              }
            }
            mandatory false;
          }
        }
        output;
      }
      tailf:action "auditlog" {
        input {
          leaf reverse {
            type empty;
            mandatory false;
          }
          leaf count {
            type uint16 {
              range "1..1024" {
                error-message "Invalid count (must be in the range 1 - 1024)";
              }
            }
            mandatory false;
          }
        }
        output;
      }
    }
  }
  container rasman {
    tailf:action "message" {
      input {
        leaf id {
          type string;
          mandatory true;
        }
      }
      output;
    }
    tailf:action "module" {
      input {
        leaf name {
          type string;
          mandatory true;
        }
      }
      output;
    }
    tailf:action "description" {
      input;
      output;
    }
    tailf:action "type" {
      input {
        leaf value {
          type enumeration {
            enum "LOG" {
              value 0;
            }
            enum "DCE" {
              value 1;
            }
            enum "FFDC" {
              value 2;
            }
            enum "AUDIT" {
              value 3;
            }
            enum "VCS" {
              value 4;
            }
          }
          mandatory true;
        }
      }
      output;
    }
  }
  rpc show-raslog {
    description
      "Shows the entries of RASLOG";
    input {
      leaf number-of-latest-events {
        type uint32;
        description
          "This specifies the number of recent events to be fetched
           from RASLOG entries.";
      }
    }
    output {
      list show-all-raslog {
        leaf number-of-entries {
          type uint32;
          description
            "This specifies the number of entries in the  be fetched";
        }
        list raslog-entries {
          leaf index {
            type uint32;
            description
              "Sequence number for the message";
          }
          leaf message-id {
            type string;
            description
              "Message identifier";
          }
          leaf date-and-time-info {
            type string;
            description
              "Date and time of the message.
               The format is: YYYY-MM-DD/HH:MM:SS.SSSS (micro seconds)";
          }
          leaf severity {
            type enumeration {
              enum "critical" {
                value 1;
              }
              enum "error" {
                value 2;
              }
              enum "warning" {
                value 3;
              }
              enum "informational" {
                value 4;
              }
              enum "debug" {
                value 5;
              }
              enum "unknown" {
                value 6;
              }
            }
            reference "swEventLevel defined in SW.mib";
            description
              "Severity of the message. Valid values include
               INFO, WARNING, ERROR, and CRITICAL.";
          }
          leaf repeat-count {
            type uint32;
            description
              "It identifies how many times this particular
               event has occurred.";
          }
          leaf message {
            type string;
            description
              "It contains the textual description of the event.";
          }
          leaf message-flag {
            type enumeration {
              enum "other" {
                value 1;
              }
              enum "unknown" {
                value 2;
              }
              enum "ffdc" {
                value 3;
              }
              enum "vcs" {
                value 4;
              }
            }
            description
              "It specifies the type of the message.";
          }
          leaf log-type {
            type enumeration {
              enum "system" {
                value 0;
              }
              enum "dce" {
                value 1;
              }
            }
            description
              "It specifies if the message is a SYSTEM or DCE log";
          }
          leaf switch-or-chassis-name {
            type string;
            description
              "Switch name for the generator of this message, or chassis";
          }
        }
      }
      leaf cmd-status-error-msg {
        type string;
      }
    }
  }
  rpc show-support-save-status {
    description
      "Information on the status of recent support save request";
    output {
      list show-support-save-status {
        leaf status {
          type enumeration {
            enum "other" {
              value 1;
            }
            enum "unknown" {
              value 2;
            }
            enum "completed" {
              value 3;
            }
            enum "inProgress" {
              value 4;
            }
            enum "error" {
              value 5;
            }
          }
          description
            "status of recent support save.";
        }
        leaf message {
          type string;
          description
            "Textual description of status of recent support save is
             as follows:
              unknown/other - Support Save is failed for
                              Unknown/undefined reason.  
              completed - The recent support save is completed successfully.
              in-progress - The support save is not yet completed.
                            It may contain the value of % completed.
              error - Specify the error message.";
        }
        leaf percentage-of-completion {
          type uint32;
          description
            "It specifies the value of % of completion.";
        }
      }
    }
  }
  rpc show-system-info {
    description
      "Shows the system information MAC etc.";
    input {
      leaf rbridge-id {
        type switchid-type;
      }
    }
    output {
      list show-system-info {
        leaf rbridge-id {
          type switchid-type;
        }
        leaf stack-mac {
          type ietfyang:mac-address;
          description
            "MAC address of the switch.";
        }
      }
    }
  }
  augment "/common-def:clear" {
    container support {
      tailf:action "support" {
        description
          "Clear support info";
        input;
        output;
      }
    }
    container logging {
      tailf:action "raslog" {
        input {
          leaf message-type {
            type enumeration {
              enum "SYSTEM" {
                value 0;
              }
              enum "DCE" {
                value 1;
              }
            }
            mandatory false;
          }
        }
        output;
      }
      tailf:action "auditlog" {
        input;
        output;
      }
    }
  }
}
