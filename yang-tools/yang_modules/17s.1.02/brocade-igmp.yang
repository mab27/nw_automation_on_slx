/*********************************************************************
 * Copyright (c) 2011 by Brocade Communications Systems, Inc.
 * All rights reserved.
 * brocade-igmp : Brocade IGMP data model
 *
 * March 2011, Abhay Gidwani
 *
 *
 ********************************************************************/
module brocade-igmp {
  namespace "urn:brocade.com:mgmt:brocade-igmp";
  prefix igmp;

  import brocade-interface {
    prefix interface;
  }
  import brocade-igmp-snooping {
    prefix igmp-snooping;
  }
  import ietf-inet-types {
    prefix inet;
  }
  import brocade-system-capabilities {
    prefix c;
  }

  organization "Brocade Communications Systems, Inc.";
  contact
    "Brocade Communications Systems, Inc.
     130 Holger Way,
     San Jose, CA 95134
     U.S.A
     Tel: +1-408-333-8000
     E-mail: info@brocade.com
     Web: www.brocade.com";
  description
    "This file defines the data model for the IGMP (Internet
     Group Management Protocol) configuration commands.";

  revision 2011-03-28 {
    description
      "Initial version of the IGMP module.";
  }
  revision 2014-06-12 {
    description
      "Enhanced CLI  version of the IGMP module.";
  }

  grouping igmp-phy-intf-cfg-cmd {
    container igmp-phy-intf-cfg {
      container igmp {
        when "(/c:capabilities/c:ip/c:igmp = \"true\")";
        leaf igmpl3-last-member-query-interval {
          type igmp-snooping:lmqt-type;
          units "milliSeconds";
          default "1000";
        }
        leaf igmpl3-query-interval {
          type igmp-snooping:qi-type;
          units "Seconds";
          default "125";
        }
        leaf igmpl3-query-max-response-time {
          type igmp-snooping:qmrt-type;
          units "Seconds";
          default "10";
        }
        leaf igmpl3-immediate-leave {
          type empty;
        }
        leaf igmpl3-version {
          type uint32 {
            range "1..3";
          }
          default "2";
        }
        list igmpl3-static-group {
          key "igmpl3-sg-addr";
          leaf igmpl3-sg-addr {
            type inet:ipv4-address;
          }
        }
      }
    }
  }

  augment "/interface:interface/interface:ethernet/interface:ip" {
    description
      "Internet Protocol (IP)";
    container igmp {
      when "(/c:capabilities/c:ip/c:igmp = \"true\")";
      uses igmp-phy-intf-cfg-cmd;
    }
  }
}
