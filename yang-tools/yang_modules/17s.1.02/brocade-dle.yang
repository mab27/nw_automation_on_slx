/*********************************************************************
 * Copyright (c) 2011 by Brocade Communications Systems, Inc.
 * All rights reserved.
 * brocade-dle.yang: Brocade delay-link-event   module data model
 *
 * March 2011, Ojasvita Parate
 *
 *
 ********************************************************************/
module brocade-dle {
  namespace "urn:brocade.com:mgmt:brocade-dle";
  prefix dle;

  import brocade-interface {
    prefix interface;
  }

  organization "Brocade Communications Systems, Inc.";
  contact
    "Brocade Communications Systems, Inc.
     Postal: 130 Holger Way
             San Jose, CA 95134
             U.S.A
     Tel: +1-408-333-8000
     E-mail: support@Brocade.com
     web: www.brocade.com.";
  description
    "This module manages delay link event (DLE)";

  revision 2010-04-28 {
    description
      "Initial version of this management module.";
  }

  grouping common-dle-cmds {
    container delay-link-event {
      container delay-link {
        leaf delay-link-event-entry {
          type uint32 {
            range "1..200";
          }
        }
        leaf delay-link-event-type {
          type enumeration {
            enum "up" {
              value 1;
            }
            enum "down" {
              value 2;
            }
            enum "both" {
              value 3;
            }
          }
        }
      }
    }
  }

  augment "/interface:interface/interface:ethernet" {
    uses common-dle-cmds;
  }
}
