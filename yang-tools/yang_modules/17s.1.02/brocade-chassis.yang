/*******************************************************************
* Copyright (c) 2016 by Brocade Communications Systems, Inc.
* All rights reserved.
*brocade-chassis.yang: FOS switchconfig  Yang model that will contain switch configurable
* enable/disable settings (i.e. chassisenable/disable, switchenable/disable)
*
* April 2010, John Rodrigues 
*
********************************************************************/
module brocade-chassis {
  namespace "urn:brocade.com:mgmt:brocade-chassis";
  prefix chassis;

  import tailf-common {
    prefix tailf;
  }
  import brocade-common-def {
    prefix common-def;
  }
  import brocade-vcs {
    prefix vcs;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "Module for implementing switch configurable
     enable/disable CLIs";

  revision 2011-04-11 {
    description
      "Initial version of this management module.";
  }

  grouping chassis-config-cmds {
    container chassis {
      leaf virtual-ip {
        type common-def:ipv4-prefix-mask;
      }
      leaf virtual-ipv6 {
        type common-def:ipv6-address-prefix;
      }
      container oper-address {
        leaf virtual-oper-Vip-address {
          type common-def:ipv4-address-prefix-type;
          config false;
          description
            "The assigned chassis IPv4 address.";
        }
        leaf-list virtual-oper-VipV6-address {
          type string;
          config false;
          description
            "The assigned chassis IPv6 address.";
        }
      }
    }
  }

  container hide-virtual-ip-holder {
    when "/vcs:vcsmode/vcs:vcs-mode = \"false\"";
    uses chassis-config-cmds;
  }
  container chassis {
    tailf:action "enable";
    tailf:action "disable";
    container beacon {
      tailf:action "enable";
      tailf:action "disable";
    }
    container fan {
      container airflow-direction {
        tailf:action "port-side-intake";
        tailf:action "port-side-exhaust";
      }
    }
  }
}
