/*************************************************************************
 *   Copyright (C) 2017-2022 Brocade Communications Systems, Inc.          *
 *   All rights reserved.                                                  *
 *   Author : swrel                                                        *
 ************************************************************************/
module brocade-sysdiag-operational {
  namespace "urn:brocade.com:mgmt:brocade-sysdiag-operational";
  prefix sysdiag-operational;

  organization "Brocade Communications Systems, Inc.";
  contact
    "Brocade Communications Systems, Inc.
     Postal:\t130 Holger Way
        San Jose, CA 95134 U.S.A
     Tel: +1-408-333-8000
     E-mail: support@Brocade.com 
     web: www.brocade.com.";
  description
    "This management module is an instrumentation to manage sysdiag";

  revision 2017-09-26 {
    description
      "First implementation of sysdiag module";
  }

  container tm-state {
    description
      "TM statistics";
    config false;
    list tmdevicestataggr {
      description
        "Get TM device stats from all towers and all slots";
      key "slot tower";
      leaf slot {
        description
          "slot id to get tm devices stats";
        type uint16;
      }
      leaf tower {
        description
          "tower id to get tm device stats";
        type uint16;
      }
      leaf ingress-total-pkt-cnt-aggr {
        description
          "ingress_total_pkt_cnt";
        type uint64;
      }
      leaf enque-pkt-cnt-aggr {
        description
          "enque_pkt_cnt";
        type uint64;
      }
      leaf deque-pkt-cnt-aggr {
        description
          "deque_pkt_cnt";
        type uint64;
      }
      leaf total-discard-pkt-cnt-aggr {
        description
          "total_discard_pkt_cnt";
        type uint64;
      }
      leaf deleted-pkt-cnt-aggr {
        description
          "deleted_pkt_cnt";
        type uint64;
      }
      leaf invalid-queue-pkt-aggr {
        description
          "invalid_queue_pkt";
        type uint64;
      }
      leaf cpu-pkt-cnt-aggr {
        description
          "cpu_pkt_cnt";
        type uint64;
      }
      leaf uni-pkt-cnt-aggr {
        description
          "uni_pkt_cnt";
        type uint64;
      }
      leaf mcast-pkt-cnt-aggr {
        description
          "mcast_pkt_cnt";
        type uint64;
      }
      leaf uni-discard-pkt-cnt-aggr {
        description
          "uni_discard_pkt_cnt";
        type uint64;
      }
      leaf mcast-discard-pkt-cnt-aggr {
        description
          "mcast_discard_pkt_cnt";
        type uint64;
      }
      leaf fqp-pkt-cnt-aggr {
        description
          "fqp_pkt_cnt";
        type uint64;
      }
      leaf ehp-discard-cnt-aggr {
        description
          "ehp_discard_cnt";
        type uint64;
      }
    }
    list non-empty-voq {
      description
        "non empty voq's in the system";
      key "slot-port";
      leaf slot-port {
        description
          "slot/port (first port on device) where queue is non empty";
        type string;
      }
      leaf voq-id {
        description
          "voq id";
        type uint32;
      }
      leaf voq-size {
        description
          "queue size";
        type uint32;
      }
    }
    list tmcpustatsslot {
      description
        "TM voq stats for CPU port per slot";
      key "slot-id cpugroup-id";
      leaf slot-id {
        description
          "slot_id";
        type uint16;
      }
      leaf cpugroup-id {
        description
          "cpugroup_id";
        type uint16;
      }
      leaf enquepkt {
        description
          "enque_pkts";
        type uint64;
      }
      leaf enqueubytes {
        description
          "enque_bytes";
        type uint64;
      }
      leaf discardpkt {
        description
          "discard_pkts";
        type uint64;
      }
      leaf discardbytes {
        description
          "discard_bytes";
        type uint64;
      }
      leaf currdepth {
        description
          "current_queue_depth";
        type uint64;
      }
      leaf maxdepth {
        description
          "max_queue_depth";
        type uint64;
      }
    }
    list tmcpustatsslotallgrp {
      description
        "TM voq stats for CPU port per slot for all CPU group";
      key "slot-id";
      leaf slot-id {
        description
          "slot_id";
        type uint16;
      }
      leaf enquepkt {
        description
          "enque_pkts";
        type uint64;
      }
      leaf enqueubytes {
        description
          "enque_bytes";
        type uint64;
      }
      leaf discardpkt {
        description
          "discard_pkts";
        type uint64;
      }
      leaf discardbytes {
        description
          "discard_bytes";
        type uint64;
      }
      leaf currdepth {
        description
          "current_queue_depth";
        type uint64;
      }
      leaf maxdepth {
        description
          "max_queue_depth";
        type uint64;
      }
    }
    list tm-top-discard-pkt-data {
      description
        "TM voq stats to get list of top discarded destination ports";
      key "slot tower id";
      leaf slot {
        description
          "slot id to get top discarded destination ports";
        type uint16;
      }
      leaf tower {
        description
          "tower id to get top discarded destination ports";
        type uint16;
      }
      leaf id {
        description
          "unique id to get top discarded destination ports";
        type uint16;
      }
      leaf dest-port {
        description
          "destination port having one of the highest discarded packets";
        type string;
      }
      leaf priority {
        description
          "priority of the highest discarded packets";
        type uint16;
      }
      leaf queue {
        description
          "Queue id that is having discarded packets";
        type uint32;
      }
      leaf discardpkt {
        description
          "count of the number of packets that are discarded";
        type uint64;
      }
    }
    list tm-top-max-queue-depth-data {
      description
        "TM voq stats to get list of top max queue depth";
      key "slot tower id";
      leaf slot {
        description
          "slot id to get top max queue depth";
        type uint16;
      }
      leaf tower {
        description
          "tower id to get top max queue depth";
        type uint16;
      }
      leaf id {
        description
          "unique id to get top max queue depth";
        type uint16;
      }
      leaf dest-port {
        description
          "destination port having one of the highest max queue depth";
        type string;
      }
      leaf priority {
        description
          "priority of the highest max queue depth";
        type uint16;
      }
      leaf queue {
        description
          "Queue id that is having max queue depth";
        type uint32;
      }
      leaf max-queue-depth {
        description
          "value of max queue depth";
        type uint32;
      }
      leaf min-threshold {
        description
          "minimum threshold value for filtering";
        type uint32;
      }
      leaf max-utilization {
        description
          "maximum buffer utilization of current destination port";
        type uint32;
      }
    }
    list tm-max-buff-util-data {
      description
        "Snapshot of max TM buffer utilzation";
      key "slot tower";
      leaf slot {
        description
          "slot id to get top discarded destination ports";
        type uint16;
      }
      leaf tower {
        description
          "tower id to get top discarded destination ports";
        type uint16;
      }
      leaf max-buff-size {
        description
          "Max size of the available buffer";
        type uint64;
      }
      leaf max-buff-util {
        description
          "Buffer utilization of maximum buffere available";
        type uint16;
      }
    }
    list tmvoqstatistics {
      description
        "Get TM VOQ statistics";
      key "ing-slot ing-tower egr-voqid";
      leaf ing-slot {
        description
          "ingress slot to get tm voq statistics";
        type uint16;
      }
      leaf ing-tower {
        description
          "ingress tpwer to get tm voq statistics";
        type uint16;
      }
      leaf egr-voqid {
        description
          "egress voq-id to get tm voq statistics";
        type uint16;
      }
      leaf priority {
        description
          "Traffic class priority for TM VOQ statistics";
        type uint16;
      }
      leaf enquepkt {
        description
          "Count of packets enqueued in TM VOQ";
        type uint64;
      }
      leaf enqueubytes {
        description
          "Count of bytes enqueued in TM VOQ";
        type uint64;
      }
      leaf discardpkt {
        description
          "Count of packets discarded for respective TM VOQ";
        type uint64;
      }
      leaf discardbytes {
        description
          "Count of bytes discarded for respective TM VOQ";
        type uint64;
      }
      leaf currdepth {
        description
          "Current queue depth size of respective TM VOQ";
        type uint64;
      }
      leaf maxdepth {
        description
          "Maxixum depth reached for respective TM VOQ";
        type uint64;
      }
    }
  }
  list cpu-interface-state {
    description
      "CPU ethernet interface stats";
    config false;
    key "ifname";
    leaf ifname {
      description
        "Interface name";
      type string;
    }
    container gos-stats {
      uses group-stats;
    }
    container host-stats {
      uses group-stats;
    }
  }

  grouping group-stats {
    description
      "CPU ethernet interface stats detail";
    leaf link-status {
      description
        "Link status";
      type string;
    }
    leaf tx-pkts-cnt {
      description
        "Tx packets counter";
      type uint64;
    }
    leaf tx-bytes-cnt {
      description
        "Tx bytes counter";
      type uint64;
    }
    leaf tx-errors-cnt {
      description
        "Tx error counter";
      type uint64;
    }
    leaf tx-drop-cnt {
      description
        "Tx drop counter";
      type uint64;
    }
    leaf tx-overrun-error-cnt {
      description
        "Tx overrun error counter";
      type uint64;
    }
    leaf tx-carrier-error-cnt {
      description
        "Tx carrier error counter";
      type uint64;
    }
    leaf rx-pkts-cnt {
      description
        "Rx packets counter";
      type uint64;
    }
    leaf rx-bytes-cnt {
      description
        "Rx bytes counter";
      type uint64;
    }
    leaf rx-errors-cnt {
      description
        "Rx errors counter";
      type uint64;
    }
    leaf rx-drop-cnt {
      description
        "Rx drop counter";
      type uint64;
    }
    leaf rx-overrun-error-cnt {
      description
        "Rx overrun error counter";
      type uint64;
    }
    leaf rx-frame-error-cnt {
      description
        "Rx frame error counter";
      type uint64;
    }
    leaf tx-aborted-error-cnt {
      description
        "Tx aborted error counter";
      type uint64;
    }
    leaf tx-fifo-error-cnt {
      description
        "Tx fifo error counter";
      type uint64;
    }
    leaf tx-timeout-cnt {
      description
        "Tx timeout counter";
      type uint64;
    }
    leaf tx-flow-control-xon-cnt {
      description
        "Tx flow control xon counter";
      type uint64;
    }
    leaf tx-flow-control-xoff-cnt {
      description
        "Tx flow control xoff counter";
      type uint64;
    }
    leaf tx-pkts-64bytes-cnt {
      description
        "Tx packets 64 bytes counter";
      type uint64;
    }
    leaf tx-pkts-64-127bytes-cnt {
      description
        "Tx packets 64 to 127 bytes counter";
      type uint64;
    }
    leaf tx-pkts-128-255bytes-cnt {
      description
        "Tx packets 128 to 255 bytes counter";
      type uint64;
    }
    leaf tx-pkts-256-511bytes-cnt {
      description
        "Tx packets 256 to 511 bytes counter";
      type uint64;
    }
    leaf tx-pkts-512-1023bytes-cnt {
      description
        "Tx packets 512 to 1023 bytes counter";
      type uint64;
    }
    leaf tx-pkts-1024bytes-max-cnt {
      description
        "Tx packets 1024 to Max bytes counter";
      type uint64;
    }
    leaf tx-bcast-pkts-cnt {
      description
        "Tx drop counter";
      type uint64;
    }
    leaf tx-mcast-pkts-cnt {
      description
        "Tx drop counter";
      type uint64;
    }
    leaf rx-crc-error-cnt {
      description
        "Rx crc error counter";
      type uint64;
    }
    leaf rx-fifo-error-cnt {
      description
        "Rx fifo error counter";
      type uint64;
    }
    leaf rx-missed-errors-cnt {
      description
        "Rx missed errors counter";
      type uint64;
    }
    leaf rx-no-dma-resource-cnt {
      description
        "Rx no dma resource";
      type uint64;
    }
    leaf rx-flow-control-xon-cnt {
      description
        "Rx flow control xon counter";
      type uint64;
    }
    leaf rx-flow-control-xoff-cnt {
      description
        "Rx flow control xoff counter";
      type uint64;
    }
    leaf rx-pkts-64bytes-cnt {
      description
        "Rx packets 64 bytes counter";
      type uint64;
    }
    leaf rx-pkts-64-127bytes-cnt {
      description
        "Rx packets 64 to 127 bytes counter";
      type uint64;
    }
    leaf rx-pkts-128-255bytes-cnt {
      description
        "Rx packets 128 to 255 bytes counter";
      type uint64;
    }
    leaf rx-pkts-256-511bytes-cnt {
      description
        "Rx packets 256 to 511 bytes counter";
      type uint64;
    }
    leaf rx-pkts-512-1023bytes-cnt {
      description
        "Rx packets 512 to 1023 bytes counter";
      type uint64;
    }
    leaf rx-pkts-1024bytes-max-cnt {
      description
        "Rx packets 1024 to Max bytes counter";
      type uint64;
    }
    leaf rx-good-pkts-cnt {
      description
        "Rx good pkts counter";
      type uint64;
    }
    leaf rx-bcast-pkts-cnt {
      description
        "Rx broadcast pkts counter";
      type uint64;
    }
    leaf rx-mcast-pkts-cnt {
      description
        "Rx multicast counter";
      type uint64;
    }
  }
}
