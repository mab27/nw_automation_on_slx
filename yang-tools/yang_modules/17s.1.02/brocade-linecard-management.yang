/****************************************************************
* Copyright (c) 2010 by Brocade Communications Systems, Inc.
* All rights reserved.
* FOS EM CLI Yang model that will contain linecard managemet  clis 
*
*  September 2011-2012, Hung Nguyen
*
*****************************************************************/
module brocade-linecard-management {
  namespace "urn:brocade.com:mgmt:brocade-linecard-management";
  prefix linecard-management;

  import tailf-common {
    prefix tailf;
  }
  import brocade-common-def {
    prefix common-def;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "This linecard management module is used to manage linecards.
     It can be used to configure, show, or turn on/off a linecard.n";

  revision 2011-09-06 {
    description
      "Initial version of this management module.";
  }

  typedef linecardid {
    type string {
      pattern "([1-9]|[1][0-6])" {
        error-message "Invalid slot number. Slot number must be in the range 1..16";
      }
    }
  }

  grouping linecard-cmds {
    container linecard {
      list linecards {
        key "linecardName";
        leaf linecardName {
          type linecardid;
          mandatory true;
        }
        leaf linecardType {
          type enumeration {
            enum "LC72X10G" {
              value 21;
            }
            enum "LC36X100G" {
              value 22;
            }
          }
        }
      }
    }
  }

  container global-lc-holder {
    uses linecard-cmds;
  }

  typedef slotnum {
    type uint32;
  }

  typedef sfmnum {
    type uint32;
  }

  augment "/common-def:show" {
    container linecardinfo {
      tailf:action "linecard" {
        input;
        output;
      }
    }
    container sfminfo {
      tailf:action "switch_fabric_module" {
        input;
        output;
      }
    }
    container mminfor {
      tailf:action "mm" {
        input;
        output;
      }
    }
    container slotsinfor {
      tailf:action "slots" {
        input;
        output;
      }
    }
  }
  container linecardservice {
    tailf:action "power-off" {
      input {
        choice blade-type {
          case linecard {
            leaf linecard {
              type slotnum;
              mandatory true;
            }
          }
          case sfm {
            leaf sfm {
              type sfmnum;
              mandatory true;
            }
          }
        }
      }
    }
    tailf:action "power-on" {
      input {
        choice blade-type {
          case linecard {
            leaf linecard {
              type slotnum;
              mandatory true;
            }
          }
          case sfm {
            leaf sfm {
              type sfmnum;
              mandatory true;
            }
          }
        }
      }
    }
  }
}
