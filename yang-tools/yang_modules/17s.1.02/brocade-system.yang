/*********************************************************************
 * Copyright (c) 2011 by Brocade Communications Systems, Inc.
 * All rights reserved.
 * brocade-system: Brocade  Data Model
 *
 * August 2011, Jaykishan Leelakrishnan 
 *
 *
 ********************************************************************/
module brocade-system {
  namespace "urn:brocade.com:mgmt:brocade-system";
  prefix system;

  import tailf-common {
    prefix tailf;
  }
  import ietf-inet-types {
    prefix inet;
  }
  import brocade-common-def {
    prefix common-def;
  }

  organization "Brocade Communications Systems, Inc.";
  contact
    "Brocade Communications Systems, Inc.
     Postal: 130 Holger Way
     San Jose, CA 95134
     U.S.A
     Tel: +1-408-333-6061
     E-mail: support@Brocade.com
     web: www.brocade.com.";
  description
    "This module defines SYSTEM related information.";

  revision 2011-08-09 {
    description
      "Added new get system uptime interface for netconf.";
  }

  rpc get-system-uptime {
    description
      "This is a functions that returns time
       since this managed entity was last re-initialized.";
    output {
      container show-system-uptime {
        leaf days {
          type common-def:time-interval-day;
          description
            "Indicates the number of days this managed 
             node is up since its last re-initialization.";
        }
        leaf hours {
          type common-def:time-interval-hour;
          description
            "Indicates the number of hours this managed 
             node is up since its last re-initialization. 
             This is in addition to the value of 
             corresponding instance of 'days'.";
        }
        leaf minutes {
          type common-def:time-interval-minute;
          description
            "Indicates the number of minutes this managed
             node is up since its last re-initialization.
             This is in addition to the values of 
             corresponding instance of 'days' and 'hours'.";
        }
        leaf seconds {
          type common-def:time-interval-sec;
          description
            "Indicates the number of seconds this managed
             node is up since its last re-initialization.
             This is in addition to the values of 
             corresponding instance of 'days', 'hours' 
             and 'minutes'.";
        }
      }
      leaf cmd-error {
        type string;
      }
    }
  }
  container host {
    tailf:action "host-ipv4" {
      input {
        leaf host-ipv4-address {
          type common-def:ipv4-address-prefix-type;
          description
            "This specifies the IPv4 address for Host 
             management interface.";
        }
        leaf host-ipv4-gateway {
          type inet:ipv4-address;
          description
            "IPv4 gateway for Host management interface.";
        }
      }
      output {
        leaf host-ipv4-msg {
          type string;
        }
      }
    }
    tailf:action "host-ipv6" {
      input {
        leaf host-ipv6-address {
          type common-def:ipv6-address-prefix;
          description
            "This specifies the IPv6 address for Host 
             management interface.";
        }
        leaf host-ipv6-gateway {
          type inet:ipv6-address;
          description
            "IPv6 gateway for Host management interface.";
        }
      }
      output {
        leaf host-ipv6-msg {
          type string;
        }
      }
    }
  }
  augment "/common-def:show" {
    container host {
      tailf:action "show-hostos-ip-address";
    }
  }
}
