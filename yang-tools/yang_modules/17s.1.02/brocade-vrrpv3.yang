/*********************************************************************
 * Copyright (c) 2013 by Brocade Communications Systems, Inc.
 * All rights reserved.
 * brocade-vrrpv3.yang: Brocade VRRP v3 data model
 *
 * Oct 2013, Ankit Jindal
 *
 *
 ********************************************************************/
module brocade-vrrpv3 {
  namespace "urn:brocade.com:mgmt:brocade-vrrpv3";
  prefix vrrpv3;

  import brocade-interface {
    prefix interface;
  }
  import brocade-ipv6-config {
    prefix ipv6-config;
  }
  import ietf-inet-types {
    prefix inet;
  }
  import brocade-common-def {
    prefix common-def;
  }
  import brocade-system-capabilities {
    prefix c;
  }

  organization "Brocade Communications Systems, Inc.";
  contact
    "Brocade Communications Systems, Inc.
     Postal: 1745 Technology Drive,
             San Jose, CA 95110
              U.S.A
     Tel: +1-408-392-6061
     E-mail: support@Brocade.com
     web: www.brocade.com.";
  description
    "This module describes the data model for Virtual Router Redundancy Protocol";

  revision 2013-10-21 {
    description
      "Initial version of this management module.";
  }

  typedef vrid-type {
    type uint8 {
      range "1..255" {
        description
          "Virtual router identifier, Range: 1-255";
      }
    }
  }

  typedef track-iftype {
    type enumeration {
      enum "ethernet" {
        value 8;
        description
          "Ethernet interface";
      }
      enum "port-channel" {
        value 3;
        description
          "Port-channel interface";
      }
    }
  }

  typedef track-ifname {
    type union {
      type interface:interface-type;
      type string {
        pattern "([1-9]|[1-9][0-9]|[1-4][0-9]{2}|50[0-9]|51[0-2])";
      }
    }
  }

  grouping vrrpv3-owner-cmds {
    container owner {
      description
        "IPv6 VRRP owner";
      leaf owner-priority {
        description
          "IPv6 VRRP owner priority";
        type uint8 {
          range "1..254";
        }
      }
      leaf owner-track-priority {
        description
          "IPv6 VRRP owner track priority";
        type uint8 {
          range "0..254";
        }
        default "0";
      }
    }
  }

  container vrrp-rbridge-global {
    leaf vrrp-acceptmode-disable {
      type empty;
      description
        "Disable accept mode  for the non owner vrrp vip";
    }
  }

  grouping global-vrrpv3-cmds {
    container proto-vrrpv3 {
      leaf vrrp {
        type empty;
        description
          "Virtual Router Redundacy Protocol IPv6 (VRRPv3)";
      }
      leaf vrrp-extended {
        type empty;
        description
          "Virtual Router Redundacy Protocol IPv6 Extended (VRRPv3-E)";
      }
    }
  }

  grouping vrrpv3-interface-cmds {
    list vrrpv3-group {
      description
        "Start vrrpv3 configuration";
      key "vrid";
      leaf vrid {
        type vrid-type;
      }
      leaf use-v2-checksum {
        type empty;
        description
          "Use v2 checksum";
      }
      uses vrrpv3-owner-cmds;
      list virtual-ip {
        key "virtual-ipaddr";
        leaf virtual-ipaddr {
          type inet:ipv6-address;
          description
            "Virtual IPv6 address";
        }
      }
      container track {
        description
          "Interface to be tracked";
        list interface {
          key "interface-type interface-name";
          leaf interface-type {
            type track-iftype;
          }
          leaf interface-name {
            type track-ifname;
          }
          leaf track-priority {
            type uint8 {
              range "1..254";
            }
            description
              "Track Priority";
          }
        }
      }
      uses vrrpv3-groups-only-cmds;
      uses vrrpv3-groups;
    }
    list vrrpv3e-group {
      when "(/c:capabilities/c:l3/c:vrrp_extended_group_phy = \"true\")";
      key "vrid";
      leaf vrid {
        type vrid-type;
      }
      container virtual-mac {
        description
          "Virtual MAC";
        leaf vmac {
          type empty;
          description
            "Virtual MAC address";
        }
      }
      list virtual-ip {
        key "virtual-ipaddr";
        leaf virtual-ipaddr {
          type inet:ipv6-address;
          description
            "Virtual IPv6 address";
        }
      }
      container track {
        description
          "Interface to be tracked";
        list interface {
          key "interface-type interface-name";
          leaf interface-type {
            type track-iftype;
          }
          leaf interface-name {
            type track-ifname;
          }
          leaf track-priority {
            type uint8 {
              range "1..254";
            }
            description
              "Track Priority";
          }
        }
      }
      uses vrrpv3-groups;
      uses vrrpv3e-cmds-only;
    }
  }

  augment "/common-def:ipv6" {
    uses global-vrrpv3-cmds;
  }

  grouping vrrpv3e-cmds-only {
    leaf advertise-backup {
      type empty;
      description
        "Enable periodic backup advertisement messages";
    }
    leaf nd-advertisement-timer {
      type uint32 {
        range "0..3600";
      }
      description
        "Neighbor Discovery Advertisment Interval";
    }
    leaf advertisement-interval-scale {
      type uint32 {
        range "1..10";
      }
      description
        "Ipv6 session advertisement interval scale factor <1|2|5|10>";
    }
    leaf backup-advertisement-interval {
      type uint32 {
        range "60..3600";
      }
      description
        "Set Backup advertisement interval";
    }
    leaf vrrpe-advertisement-interval {
      type uint32 {
        range "1..255";
      }
      description
        "Set advertisement interval";
    }
    container short-path-forwarding {
      description
        "Enable backup router to send traffic";
      leaf basic {
        type empty;
      }
      leaf revert-priority {
        type uint8 {
          range "1..254";
        }
        description
          "Set revert priority";
      }
    }
  }

  grouping vrrpv3-vcs-cmds {
    leaf priority {
      type uint8 {
        range "1..254";
      }
      description
        "Set router priority within virtual router";
    }
    leaf description {
      type string {
        length "1..64" {
          description
            "Characters describing this interface (Max Size - 64)";
        }
      }
      description
        "Interface specific description";
    }
  }

  grouping vrrpv3-groups-only-cmds {
    leaf advertisement-interval {
      type uint32 {
        range "100..40900";
      }
      description
        "Set advertisement interval";
    }
  }

  grouping vrrpv3-groups {
    leaf enable {
      type empty;
      description
        "Enable Session";
    }
    leaf hold-time {
      type uint32 {
        range "1..3600";
      }
      description
        "Configure hold time for this session";
    }
    leaf preempt-mode {
      type empty;
      description
        "Set preempt mode for the session";
    }
    uses vrrpv3-vcs-cmds;
  }

  augment "/interface:interface/interface:ethernet/interface:ipv6" {
    uses vrrpv3-interface-cmds;
  }
  augment "/common-def:routing-system/interface:interface/interface:ve/ipv6-config:ipv6" {
    list vrrpv3 {
      key "vrid";
      leaf vrid {
        type vrid-type;
      }
      leaf use-v2-checksum {
        type empty;
        description
          "Use v2 checksum";
      }
      uses vrrpv3-owner-cmds;
      list virtual-ip {
        key "virtual-ipaddr";
        leaf virtual-ipaddr {
          type inet:ipv6-address;
          description
            "Virtual IPv6 address";
        }
      }
      container track {
        description
          "Interface to be tracked";
        list interface {
          key "interface-type interface-name";
          leaf interface-type {
            type track-iftype;
          }
          leaf interface-name {
            type track-ifname;
          }
          leaf track-priority {
            type uint8 {
              range "1..254";
            }
            description
              "Track Priority";
          }
        }
      }
      uses vrrpv3-groups-only-cmds;
      uses vrrpv3-groups;
    }
    list vrrpv3e {
      key "vrid";
      leaf vrid {
        type vrid-type;
      }
      container virtual-mac {
        description
          "Virtual MAC";
        leaf vmac {
          type empty;
          description
            "Virtual MAC address";
        }
      }
      list virtual-ip {
        key "virtual-ipaddr";
        leaf virtual-ipaddr {
          type inet:ipv6-address;
          description
            "Virtual IPv6 address";
        }
      }
      container track {
        description
          "Interface to be tracked";
        list network {
          key "network-address";
          leaf network-address {
            type common-def:ipv6-address-prefix;
            description
              "IPv6 global address";
          }
          leaf network-priority {
            type uint8 {
              range "1..254";
            }
          }
        }
        list interface {
          key "interface-type interface-name";
          leaf interface-type {
            type track-iftype;
          }
          leaf interface-name {
            type track-ifname;
          }
          leaf track-priority {
            type uint8 {
              range "1..254";
            }
            description
              "Track Priority";
          }
        }
      }
      uses vrrpv3-groups;
      uses vrrpv3e-cmds-only;
    }
  }
}
