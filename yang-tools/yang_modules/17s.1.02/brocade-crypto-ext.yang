/*************************************************************************
 *   Copyright (C) 2014 Brocade Communications Systems, Inc.               *
 *   All rights reserved.                                                  *
 *   Author : Soundarya Ravi                                               *
 *************************************************************************/
module brocade-crypto-ext {
  namespace "urn:brocade.com:mgmt:brocade-crypto-ext";
  prefix brcd-crypto-ext;

  import tailf-common {
    prefix tailf;
  }
  import brocade-common-def {
    prefix common-def;
  }
  import ietf-inet-types {
    prefix inet;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "Instrument to configure Crypto services for HTTPS Certificate Management";

  revision 2014-07-01 {
    description
      "Initial version of this module.";
  }

  grouping cert_parameters {
    leaf protocol {
      description
        "Protocol";
      type enumeration {
        enum "SCP";
        enum "FTP";
      }
      mandatory true;
    }
    leaf user {
      description
        "Username";
      type string;
      mandatory true;
    }
    leaf password {
      description
        "Password";
      type string;
    }
    leaf host {
      description
        "Hostname/IP address";
      type inet:host;
      mandatory true;
    }
    leaf directory {
      description
        "Remote Directory";
      type string;
      mandatory true;
    }
  }

  grouping gencsr_parameters {
    leaf country {
      type string {
        length "1..2";
      }
      mandatory true;
    }
    leaf state {
      type string {
        length "1..20";
      }
      mandatory true;
    }
    leaf locality {
      type string;
      mandatory true;
    }
    leaf organization {
      type string;
      mandatory true;
    }
    leaf orgunit {
      type string;
      mandatory true;
    }
    leaf common {
      type inet:host;
      mandatory true;
    }
  }

  container crypto {
    container ca {
      tailf:action "authenticate" {
        input {
          container authenticate_params {
            leaf trustpoint {
              type string {
                length "1..64" {
                  error-message
                    "Trustpoint name length should be in the
                     range 1-64";
                }
              }
              mandatory true;
            }
            uses cert_parameters;
            leaf file {
              description
                "Certificate file in PEM format";
              type string;
              mandatory true;
            }
          }
        }
      }
      tailf:action "enroll" {
        input {
          container authenticate_params {
            leaf trustpoint {
              type string {
                length "1..64" {
                  error-message
                    "Trustpoint name length should be in the
                     range 1-64";
                }
              }
              mandatory true;
            }
            uses gencsr_parameters;
            uses cert_parameters;
          }
        }
      }
      tailf:action "import" {
        input {
          container authenticate_params {
            leaf trustpoint {
              type string {
                length "1..64" {
                  error-message
                    "Trustpoint name length should be in the
                     range 1-64";
                }
              }
              mandatory true;
            }
            leaf certificate {
              type empty;
              mandatory true;
            }
            uses cert_parameters;
            leaf file {
              description
                "Certificate file in PEM format";
              type string;
              mandatory true;
            }
          }
        }
      }
    }
  }
  augment "/common-def:no" {
    container nocrypto {
      container ca {
        tailf:action "authenticate" {
          input {
            container authenticate_params {
              leaf trustpoint {
                type string {
                  length "1..64" {
                    error-message
                      "Trustpoint name length should be in the
                       range 1-64";
                  }
                }
                mandatory true;
              }
            }
          }
        }
        tailf:action "import" {
          input {
            container authenticate_params {
              leaf trustpoint {
                type string {
                  length "1..64" {
                    error-message
                      "Trustpoint name length should be in the
                       range 1-64";
                  }
                }
                mandatory true;
              }
              leaf certificate {
                type empty;
                mandatory true;
              }
            }
          }
        }
      }
    }
  }
  augment "/common-def:show" {
    container crypto {
      container key {
        tailf:action "mypubkey" {
          input;
        }
      }
      container ca {
        tailf:action "trustpoint" {
          input;
        }
        tailf:action "certificates" {
          input;
        }
      }
    }
  }
}
