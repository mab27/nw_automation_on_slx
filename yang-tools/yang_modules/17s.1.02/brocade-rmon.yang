/*********************************************************************
 * Copyright (c) 2011 by Brocade Communications Systems, Inc.
 * All rights reserved.
 * brocade-rmon.yang-: Brocade RMON MIB Data Model
 *
 * April 2011, Andy Bierman
 *
 *
 ********************************************************************/
module brocade-rmon {
  namespace "urn:brocade.com:mgmt:brocade-rmon";
  prefix rmon;

  import brocade-interface {
    prefix interface;
  }

  revision 2011-02-28 {
    description
      "Initial version";
  }

  container rmon {
    list event-entry {
      key "event-index";
      leaf event-index {
        type event-index-type;
      }
      leaf event-description {
        type event-description-type;
        default "__default_description";
      }
      leaf log {
        type empty;
      }
      leaf event-community {
        type string {
          length "1 .. 127";
        }
        default "__default_community";
      }
      leaf event-owner {
        type owner-string;
      }
    }
    list alarm-entry {
      key "alarm-index";
      leaf alarm-index {
        type alarm-index-type;
      }
      leaf snmp-oid {
        mandatory true;
        type snmp-oid-type;
      }
      leaf alarm-interval {
        mandatory true;
        type uint32 {
          range "1 .. 2147483648";
        }
      }
      leaf alarm-sample {
        mandatory true;
        type alarm-sample-type;
      }
      leaf alarm-rising-threshold {
        mandatory true;
        type uint32 {
          range "0 .. 4294967295";
        }
      }
      leaf alarm-rising-event-index {
        mandatory true;
        type alarm-rising-event-index-type;
      }
      leaf alarm-falling-threshold {
        type uint32 {
          range "0 .. 4294967295";
        }
        default "0";
      }
      leaf alarm-falling-event-index {
        type alarm-falling-event-index-type;
      }
      leaf alarm-owner {
        type owner-string;
      }
    }
  }

  grouping common-rmon-cmds {
    container rmon {
      container collection {
        list ether-stats-entry {
          key "ether-stats-index";
          leaf ether-stats-index {
            type ether-stats-index-type;
          }
          leaf ether-stats-owner {
            type owner-string;
          }
        }
        list history-control-entry {
          key "history-control-index";
          leaf history-control-index {
            type history-control-index-type;
          }
          leaf history-control-buckets-requested {
            type history-control-buckets-requested-type;
            default "50";
          }
          leaf history-control-interval {
            type history-control-interval-type;
            default "1800";
          }
          leaf history-control-owner {
            type owner-string;
          }
        }
      }
    }
  }

  augment "/interface:interface/interface:ethernet" {
    uses common-rmon-cmds;
  }

  typedef owner-string {
    type string {
      pattern "[a-zA-Z]{1}([-a-zA-Z0-9\\.\\\\\\\\@#\\+\\*\\(\\)=\\{~\\}%<>=$_\\[\\]\\|]{0,14})";
      length "1 .. 15";
    }
  }

  typedef ether-stats-index-type {
    type int32 {
      range "1 .. 65535";
    }
  }

  typedef history-control-index-type {
    type int32 {
      range "1 .. 65535";
    }
  }

  typedef history-control-buckets-requested-type {
    type int32 {
      range "1 .. 65535";
    }
  }

  typedef history-control-interval-type {
    type int32 {
      range "1 .. 3600";
    }
  }

  typedef alarm-index-type {
    type int32 {
      range "1 .. 65535";
    }
  }

  typedef alarm-sample-type {
    type enumeration {
      enum "absolute" {
        value 1;
      }
      enum "delta" {
        value 2;
      }
    }
  }

  typedef alarm-rising-event-index-type {
    type int32 {
      range "1 .. 65535";
    }
  }

  typedef alarm-falling-event-index-type {
    type int32 {
      range "1 .. 65535";
    }
  }

  typedef event-index-type {
    type int32 {
      range "1 .. 65535";
    }
  }

  typedef event-description-type {
    type string {
      length "min .. 127";
    }
  }

  typedef snmp-oid-type {
    type string {
      length "min .. 35";
    }
  }
}
