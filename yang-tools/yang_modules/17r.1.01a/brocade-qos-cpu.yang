/*********************************************************************
 * Copyright (c) 2016 by Brocade Communications Systems, Inc.
 * All rights reserved.
 * brocade-qos-cpu.yang: Brocade QOS CPU module data model
 *
 * Jan 2016, Michael Li
 *
 *
 ********************************************************************/
module brocade-qos-cpu {
  namespace "urn:brocade.com:mgmt:brocade-qos-cpu";
  prefix qos-cpu;

  import brocade-qos-mls {
    prefix qos-mls;
  }

  organization "Brocade Communications Systems, Inc.";
  contact
    "Brocade Communications Systems, Inc.
     Postal: 130 Holger Way
             San Jose, CA 95134
             U.S.A
     Tel: +1-408-333-8000
     E-mail: support@Brocade.com 
     web: www.brocade.com.";
  description
    "This module manages CPU Quality Of Service (QOS)";

  revision 2016-01-28 {
    description
      "Initial version of this management module.";
  }

  typedef slotid {
    type string {
      length "1..3" {
        error-message "Invalid slotid (must be in the range 0-8) or all";
      }
    }
  }

  typedef groupid {
    type string {
      length "1..3";
    }
  }

  typedef priority {
    type string {
      length "1..3" {
        error-message "Invalid priority (must be in the range 0-7) or all";
      }
    }
  }

  typedef shaper-rate {
    type uint32 {
      range "1..1000000";
    }
  }

  typedef burst-size {
    type uint8 {
      range "1..64";
    }
  }

  typedef port-burst-size {
    type uint8 {
      range "1..31";
    }
  }

  typedef weight-value {
    type uint8 {
      range "1..128";
    }
  }

  augment "/qos-mls:qos" {
    container cpu {
      list slot {
        key "slot-id";
        leaf slot-id {
          type slotid;
        }
        container port-group {
          container port {
            container port-shaper {
              leaf port-shaper-rate {
                type shaper-rate;
              }
              leaf port-shaper-burst-size {
                type port-burst-size;
              }
            }
          }
          list group {
            key "group-id";
            leaf group-id {
              type groupid;
            }
            container group-config-shaper-wfq {
              container group-shaper {
                leaf group-shaper-rate {
                  type shaper-rate;
                }
                leaf group-shaper-burst-size {
                  type burst-size;
                }
              }
              container group-wfq {
                leaf group-wfq-weight {
                  type weight-value;
                }
              }
              list group-prio {
                key "group-prio-id";
                leaf group-prio-id {
                  type priority;
                }
                container group-prio-config-shaper-wfq {
                  container group-prio-shaper {
                    leaf group-prio-shaper-rate {
                      type shaper-rate;
                    }
                    leaf group-prio-shaper-burst-size {
                      type burst-size;
                    }
                  }
                  container group-prio-wfq {
                    leaf group-prio-wfq-weight {
                      type weight-value;
                    }
                  }
                }
              }
            }
          }
        }
      }
    }
  }
}
