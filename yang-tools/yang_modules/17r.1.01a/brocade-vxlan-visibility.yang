/*********************************************************************
 * Copyright (c) 2015 by Brocade Communications Systems, Inc.
 * All rights reserved.
 * brocade-vxlan-visibility.yang: Brocade VxLan Visibility module data model
 *
 * April 2015, Youn-Mor Chen
 *
 *
 ********************************************************************/
module brocade-vxlan-visibility {
  namespace "urn:brocade.com:mgmt:brocade-vxlan-visibility";
  prefix vxlan-visibility;

  import brocade-interface {
    prefix interface;
  }
  import brocade-common-def {
    prefix common-def;
  }
  import ietf-inet-types {
    prefix inet;
  }

  organization "Brocade Communications Systems, Inc.";
  contact
    "Brocade Communications Systems, Inc.
     Postal: 130 Holger Way
             San Jose, CA 95134
             U.S.A
     Tel: +1-408-333-8000
     E-mail: support@Brocade.com 
     web: www.brocade.com.";
  description
    "This module manages VxLan Visibility commands";

  revision 2015-06-15 {
    description
      "Initial version of this management module.";
  }

  typedef user-acl-name-type {
    type string {
      pattern "[a-zA-Z]{1}([-a-zA-Z0-9_]{0,62})";
    }
  }

  typedef user-transit-name-type {
    type string {
      pattern "[a-zA-Z]{1}([-a-zA-Z0-9_]{0,62})";
    }
  }

  container overlay {
    container access-list {
      container type {
        container vxlan {
          list standard {
            key "user-acl-name";
            leaf user-acl-name {
              type user-acl-name-type;
            }
            list seq {
              key "seq-num";
              leaf seq-num {
                type uint32 {
                  range "1 .. 65535";
                }
              }
              leaf permit-deny {
                type enumeration {
                  enum "permit" {
                    value 1;
                  }
                  enum "deny" {
                    value 2;
                  }
                }
              }
              choice choice-dst-vtep-ip {
                case case-dst-vtep-ip {
                  leaf dst-vtep-ip {
                    type inet:ipv4-address;
                  }
                }
                case case-dst-vtep-ip-any {
                  leaf dst-vtep-ip-any {
                    type empty;
                  }
                }
              }
              choice choice-src-vtep-ip {
                case case-src-vtep-ip {
                  leaf src-vtep-ip {
                    type inet:ipv4-address;
                  }
                }
                case case-src-vtep-ip-any {
                  leaf src-vtep-ip-any {
                    type empty;
                  }
                }
              }
              choice choice-vni {
                case case-vni {
                  leaf vni {
                    type uint32 {
                      range "1 .. 16777215";
                    }
                  }
                }
                case case-vni-any {
                  leaf vni-any {
                    type empty;
                  }
                }
              }
              leaf vni-mask {
                type string {
                  pattern "0|[1-9a-fA-F][0-9a-fA-F]{0,5}";
                }
              }
              leaf count {
                type empty;
              }
              leaf redirect {
                type interface:interface-type;
              }
              leaf sflow {
                type empty;
              }
            }
          }
          list extended {
            key "ext-user-acl-name";
            leaf ext-user-acl-name {
              type user-acl-name-type;
            }
            list ext-seq {
              key "ext-seq-num";
              leaf ext-seq-num {
                type uint32 {
                  range "1 .. 65535";
                }
              }
              leaf ext-permit-deny {
                type enumeration {
                  enum "permit" {
                    value 1;
                  }
                  enum "deny" {
                    value 2;
                  }
                }
              }
              choice choice-ext-dst-vtep-ip {
                case case-ext-dst-vtep-ip {
                  leaf ext-dst-vtep-ip {
                    type inet:ipv4-address;
                  }
                }
                case case-ext-dst-vtep-ip-any {
                  leaf ext-dst-vtep-ip-any {
                    type empty;
                  }
                }
              }
              choice choice-ext-src-vtep-ip {
                case case-ext-src-vtep-ip {
                  leaf ext-src-vtep-ip {
                    type inet:ipv4-address;
                  }
                }
                case case-ext-src-vtep-ip-any {
                  leaf ext-src-vtep-ip-any {
                    type empty;
                  }
                }
              }
              choice choice-ext-vni {
                case case-ext-vni {
                  leaf ext-vni {
                    type uint32 {
                      range "1 .. 16777215";
                    }
                  }
                }
                case case-ext-vni-any {
                  leaf ext-vni-any {
                    type empty;
                  }
                }
              }
              leaf ext-vni-mask {
                type string {
                  pattern "0|[1-9a-fA-F][0-9a-fA-F]{0,5}";
                }
              }
              leaf ext-count {
                type empty;
              }
              leaf ext-mirror {
                type interface:interface-type;
              }
              leaf ext-redirect {
                type interface:interface-type;
              }
              leaf ext-sflow {
                type empty;
              }
              leaf native {
                type empty;
              }
              leaf tag {
                type enumeration {
                  enum "none" {
                    value 1;
                  }
                  enum "single" {
                    value 2;
                  }
                  enum "any" {
                    value 3;
                  }
                }
              }
              choice choice-dst-ip {
                case case-dst-ip-host {
                  leaf dst-ip-host {
                    type inet:ipv4-address;
                  }
                }
                case case-dst-ip {
                  leaf dst-ip {
                    type union {
                      type common-def:ipv4-prefix-mask;
                      type inet:ipv4-prefix;
                    }
                  }
                }
                case case-dst-ip-any {
                  leaf dst-ip-any {
                    type empty;
                  }
                }
              }
              choice choice-src-ip {
                case case-src-ip-host {
                  leaf src-ip-host {
                    type inet:ipv4-address;
                  }
                }
                case case-src-ip {
                  leaf src-ip {
                    type union {
                      type common-def:ipv4-prefix-mask;
                      type inet:ipv4-prefix;
                    }
                  }
                }
                case case-src-ip-any {
                  leaf src-ip-any {
                    type empty;
                  }
                }
              }
              choice choice-dst-port {
                case case-dst-port {
                  leaf dst-port {
                    type uint32;
                  }
                }
                case case-dst-port-any {
                  leaf dst-port-any {
                    type empty;
                  }
                }
              }
              choice choice-src-port {
                case case-src-port {
                  leaf src-port {
                    type uint32;
                  }
                }
                case case-src-port-any {
                  leaf src-port-any {
                    type empty;
                  }
                }
              }
            }
          }
        }
      }
    }
  }
  list overlay-transit {
    key "user-transit-name";
    leaf user-transit-name {
      type user-transit-name-type;
    }
    list transit-overlay {
      key "access-group in-out";
      leaf access-group {
        type string {
          pattern "[a-zA-Z]{1}([-a-zA-Z0-9_]{0,62})";
        }
      }
      leaf in-out {
        type enumeration {
          enum "in" {
            value 1;
          }
          enum "out" {
            value 2;
          }
        }
      }
    }
  }
}
