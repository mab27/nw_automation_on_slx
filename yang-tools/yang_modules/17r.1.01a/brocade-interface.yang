/*********************************************************************
 * Copyright (c) 2012 by Brocade Communications Systems, Inc.
 * All rights reserved.
 * brocade-interface.yang: Brocade Interface Management Data Model
 *
 * July 2011, Senthil Kumar Balasubramaniam, Sanjeev C Joshi 
 *
 *
 ********************************************************************/
module brocade-interface {
  namespace "urn:brocade.com:mgmt:brocade-interface";
  prefix brocade-interface;

  import ietf-inet-types {
    prefix inet;
  }
  import brocade-common-def {
    prefix common-def;
  }
  import brocade-system-capabilities {
    prefix cap;
  }

  organization "Brocade Communications Systems, Inc.";
  contact
    "Brocade Communications Systems, Inc.
     Postal: 130 Holger Way
             San Jose, CA 95134
              U.S.A
     Tel: +1-408-333-8000
     E-mail: support@Brocade.com 
     web: www.brocade.com.";
  description
    "This management module is an instrumentation to manage  
     ethernet network interfaces sub-layers.
             
     The following ethernet interfaces can be managed using this 
     management module:
             
     +--------------------------------------------------------------+
     | List name                  Description                       |
     +--------------------------------------------------------------+
     | ethernet                   Physical Ethernet interfaces      |
     | port-channel               Port-channel/LAG interfaces       |
     | management                 Management port/interfaces        |
     | vlan                       L2 Vlan interface.                |
     +--------------------------------------------------------------+
             
     This module provides mechanism:
        - to discover and characterize the interface sub-layers.
        - to configure various attributes of these interfaces.
        - to structure the interfaces such that various L2/L3 
        access/security policies, network discovery policies, QoS 
        policies and Link aggregation policies can be applied using 
        other modules supported by the managed entity.
             
     Glossary of the terms used:
     --------------------------- 
     TRILL   - Transparent Interconnection of Lots of Links.
     VLAN    - Virtual Local Area Network.
     ISL     - Inter switch Link.
     MTU     - Maximum transmission unit. The size of the largest 
              packet which can be sent/received on an interface.
     LAG     - IEEE Link Aggregation (IEEE 802.1AX).
     vLAG    - virtual LAG.";
  reference
    "K. McCloghrie, 'The Interfaces Group MIB', RFC 2863, 
     June 2000.";

  revision 2012-04-24 {
    description
      "Deprecated .../switchport/trunk/allowed/vlanoper.";
  }
  revision 2015-09-10 {
    description
      "Added Tunable-sfpp-optics CLI.";
  }

  typedef ui32-vlan-20k-range {
    type string {
      pattern "(([1-9][0-9]{0,2})|([1-3][0-9]{3})|(40[0-8][0-9])|(4090))(-((1[0-9]{1,2})|([2-9][0-9]{0,2})|([1-3][0-9]{3})|(40[0-8][0-9])|(4090)))?((,((1[0-9]{1,2})|([2-9][0-9]{0,2})|([1-3][0-9]{3})|(40[0-8][0-9])|(4090))(-((1[0-9]{1,2})|([2-9][0-9]{0,2})|([1-3][0-9]{3})|(40[0-8][0-9])|(4090)))?)?)*";
      length "1..20000";
    }
    description
      "The definition for specifying the vlan range.";
  }

  typedef ui32-vlan-range {
    type string {
      pattern "(([1-9][0-9]{0,2})|([1-3][0-9]{3})|(40[0-8][0-9])|(4090))(-((1[0-9]{1,2})|([2-9][0-9]{0,2})|([1-3][0-9]{3})|(40[0-8][0-9])|(4090)))?((,((1[0-9]{1,2})|([2-9][0-9]{0,2})|([1-3][0-9]{3})|(40[0-8][0-9])|(4090))(-((1[0-9]{1,2})|([2-9][0-9]{0,2})|([1-3][0-9]{3})|(40[0-8][0-9])|(4090)))?)?)*";
      length "1..253";
    }
    description
      "The definition for specifying the vlan range.";
  }

  typedef ui32-1k-vlan-range {
    type string {
      pattern "(([1-9][0-9]{0,2})|([1-3][0-9]{3})|(40[0-8][0-9])|(4090))(-((1[0-9]{1,2})|([2-9][0-9]{0,2})|([1-3][0-9]{3})|(40[0-8][0-9])|(4090)))?((,((1[0-9]{1,2})|([2-9][0-9]{0,2})|([1-3][0-9]{3})|(40[0-8][0-9])|(4090))(-((1[0-9]{1,2})|([2-9][0-9]{0,2})|([1-3][0-9]{3})|(40[0-8][0-9])|(4090)))?)?)*";
      length "1..1000";
    }
    description
      "The definition for specifying the vlan range.";
  }

  typedef port-group-type {
    type string {
      pattern "((([0-9]|[1][0-6]))/([1-9]|[1-9][0-9]))";
      length "3..16";
    }
    description
      "The definition for specifying a network interface name in
       a VCS environment. It is in 2-tuple canonical format:
       slot/port-group.";
  }

  typedef interface-type {
    type string {
      pattern "((([0-9]|[1][0-6]))/([1-9]|[1-9][0-9]|[1-9][0-9][0-9])(:[1-4])?)";
      length "3..16";
    }
    description
      "The definition for specifying a network interface name in
       a VCS environment. It is in 2-tuple canonical format:
       slot/port.";
  }

  typedef standalone-man-interface-type {
    type string {
      pattern "([0-2])";
      length "1";
    }
    description
      "The definition for specifying a management network 
       interface name.";
  }

  typedef man-interface-type {
    type string {
      pattern "([1-9]|[1-9][0-9]|1[0-9][0-9]|2[0-3][0-9])/([0-9]|[1-9][0-9])";
      length "3..16";
    }
    description
      "The definition for specifying a management network 
       interface name.";
  }

  typedef vlan-type {
    type uint32 {
      range "1..4090";
    }
    description
      "The definition for specifying a vlan identifier. This 
       represents it represents an IEEE 802.1Q VLAN-ID.";
    reference
      "IEEE Std 802.1Q 2003 Edition, Virtual Bridged Local Area 
       Networks.";
  }

  typedef bd-type {
    type uint32 {
      range "1..4096";
    }
    description
      "The definition for specifying a bridge-domain  identifier.";
  }

  typedef native-vlan-type {
    type uint32 {
      range "2..4090";
    }
    description
      "The definition for specifying a vlan identifier for native vlan.";
  }

  typedef ve-type {
    type uint32 {
      range "1..4096";
    }
    description
      "The definition for specifying a ve identifier.";
  }

  typedef portchannel-type {
    type uint32 {
      range "1..512";
    }
    description
      "The definition for specifying a port-channel.";
  }

  typedef mtu-type {
    type uint32 {
      range "1548..9216";
    }
    units "Bytes";
    description
      "The definition for specifying the MTU in octets.";
  }

  typedef port-sec-violation {
    type enumeration {
      enum "restrict" {
        value 1;
        description
          "Set the action as restrict";
      }
      enum "shutdown" {
        value 2;
        description
          "Set the action as Shutdown.";
      }
    }
    description
      "The definition for specifying the violation of a 
       port-security.";
  }

  typedef po-mode {
    type enumeration {
      enum "active" {
        value 1;
        description
          "LACP negotiation enabled on a port.";
      }
      enum "passive" {
        value 2;
        description
          "LACP negotiation disabled on a port.";
      }
      enum "on" {
        value 3;
        description
          "LACP static link aggregation enabled on a port.";
      }
    }
    description
      "The definition for specifying the mode of a 
       port-channel.";
  }

  typedef po-type {
    type enumeration {
      enum "standard" {
        value 1;
        description
          "Standards (IEEE 802.3ad) based LAG.";
      }
    }
    description
      "The definition for specifying the type of a port-channel.";
  }

  typedef switchport-mode-type {
    type enumeration {
      enum "unknown" {
        value 0;
        description
          "Switchport in Unknown mode.";
      }
      enum "access" {
        value 1;
        description
          "Switchport in Access mode.";
      }
      enum "trunk" {
        value 2;
        description
          "Switchport in Trunk mode.";
      }
      enum "converged" {
        value 3;
        description
          "Switchport in Converged mode.";
      }
      enum "pvlan-promiscuous" {
        value 4;
        description
          "Switchport in PVLAN promiscuous mode.";
      }
      enum "pvlan-trunk-promiscuous" {
        value 5;
        description
          "Switchport in PVLAN trunk promiscuous mode.";
      }
      enum "pvlan-host" {
        value 6;
        description
          "Switchport in PVLAN host mode.";
      }
      enum "pvlan-trunk-host" {
        value 7;
        description
          "Switchport in PVLAN trunk host mode.";
      }
      enum "pvlan-trunk" {
        value 8;
        description
          "Switchport in PVLAN trunk mode.";
      }
      enum "trunk-no-default-native" {
        value 9;
        description
          "Switchport in trunk-no-default-native mode";
      }
    }
    description
      "The definition for specifying the mode of operation of the 
       Layer2 ethernet port.";
  }

  typedef l2-mode-type {
    type enumeration {
      enum "access" {
        value 1;
        description
          "Layer2 port in 'access' mode.";
      }
      enum "trunk" {
        value 2;
        description
          "Layer2 port in 'trunking' mode.";
      }
      enum "trunk-no-default-native" {
        value 9;
        description
          "Layer2 port in 'trunk-no-default-native' mode.";
      }
    }
    description
      "The definition for specifying the mode of operation of the 
       Layer2 ethernet port.
                   
       The ports are assigned to a single VLAN. These ports are 
       referred to as access ports and provide a connection for 
       end users or node devices.
                   
       The trunk links are required to pass VLAN information 
       between switches.";
  }

  typedef mac-address-type {
    type string {
      pattern "[0-9a-fA-F]{4}(\\.[0-9a-fA-F]{4}){2}";
    }
  }

  typedef bfd-tx-interval-type {
    type uint32 {
      range "50..30000";
    }
    description
      "The definition for specifying BFD tx-interval.";
  }

  typedef bfd-rx-interval-type {
    type uint32 {
      range "50..30000";
    }
    description
      "The definition for specifying BFD rx-interval.";
  }

  typedef bfd-multiplier-type {
    type uint32 {
      range "3..50";
    }
    description
      "The definition for specifying BFD time multiplier.";
  }

  typedef tunable-optics-sfpp-channel-type {
    type uint32 {
      range "0..102";
    }
    description
      "The definition for specifying Tunable SFPP channel number.";
  }

  container interface {
    description
      "All the interface related elements of this managed device
       grouped under this container.";
  }
  container interface-vlan {
    description
      "An intermediary node that separates the vlan related 
       elements of this managed device.";
  }
  container protocol;

  grouping interface-name-info {
    description
      "This denotes an interface name qualified with the type of 
       the interface. This grouping can be used to indicate 
       physical or logical interfaces.";
    leaf interface-type {
      type enumeration {
        enum "unknown" {
          value 1;
        }
        enum "ethernet" {
          value 10;
        }
        enum "port-channel" {
          value 5;
        }
        enum "l2vlan" {
          value 6;
        }
        enum "loopback" {
          value 7;
        }
        enum "fibrechannel" {
          value 8;
        }
        enum "tunnel" {
          value 12;
        }
      }
      description
        "The type of the interface. An 'unknown' type 
         represents error scenario and should not be used.";
    }
    leaf interface-name {
      type union {
        type brocade-interface:interface-type;
        type brocade-interface:portchannel-type;
        type brocade-interface:vlan-type;
      }
      description
        "The Interface value. The interface value is always 
         interpreted within the context of the value of 
         'interface-type' leaf:
         
         interface-type         interface-name
         -----------------      --------------------
         ethernet               slot/port
         port-channel           Port channel ID
         l2vlan                 Vlan ID
         unknown                Zero-length string.
         
         The value of an 'interface-name' must always be 
         consistent with the value of the associated 
         'interface-type'.  Attempts to set an interface-name
         to a value inconsistent with the associated 
         'interface-type' must fail with an error.";
    }
  }

  augment "/interface-vlan" {
    list vlan {
      key "name";
      description
        "The list of vlans in the managed device. Each row 
         represents a vlan. User can create/delete an entry in 
         to this list.";
      leaf name {
        type vlan-type;
        description
          "The vlan identifier.";
      }
      leaf statistics {
        type empty;
        description
          "Enable vlan statistics.";
      }
      leaf loop-detection {
        type empty;
        description
          "Enable loop detection.";
      }
      container router-interface {
        leaf ve-config {
          type ve-type;
          description
            "Ve";
        }
      }
    }
  }

  grouping interface-vrf-config {
    container vrf {
      leaf forwarding {
        type common-def:vrf-name;
        description
          "This specifies the VRF that needs to be associated
           with interface.";
      }
    }
  }

  grouping phy-interface-parameters {
    leaf speed {
      type enumeration {
        enum "auto" {
          value 0;
          description
            "Auto Detected.";
        }
        enum "1000" {
          value 1;
          description
            "1 Gigabit per second.";
        }
        enum "10000" {
          value 2;
          description
            "10 Gigabit per second.";
        }
        enum "40000" {
          value 3;
          description
            "40 Gigabit per second.";
        }
        enum "100000" {
          value 4;
          description
            "100 Gigabit per second.";
        }
        enum "100" {
          value 5;
          description
            "100 Megabit per second.";
        }
        enum "1000-auto" {
          value 8;
          description
            "1Gbps AN (802.3 Clause 37 Auto-Negotiation)";
        }
      }
      description
        "This leaf specifies the administratively configured
         bandwidth for this physical interface.";
    }
  }

  augment "/interface" {
    list ethernet {
      ordered-by user;
      key "name";
      description
        "The list of Ethernet interfaces in the 
         managed device. Each row represents a Ethernet 
         interface. The list provides a way to discover all the 
         physical interfaces in a managed device.";
      leaf name {
        type interface-type;
      }
      uses phy-interface-parameters;
    }
    list port-channel {
      ordered-by user;
      key "name";
      description
        "The list of port-channels in the managed device. Each
         entry represents a port-channel.";
      leaf name {
        type portchannel-type;
        description
          "The port-channel identifier.";
      }
      leaf po-speed {
        type enumeration {
          enum "1000" {
            value 1;
            description
              "1Gbps.";
          }
          enum "10000" {
            value 2;
            description
              "10Gbps.";
          }
          enum "40000" {
            value 3;
            description
              "40Gbps.";
          }
          enum "100000" {
            value 4;
            description
              "100Gbps.";
          }
          enum "100" {
            value 5;
            description
              "100Mbps.";
          }
        }
        default "10000";
        description
          "This specifies the administratively configured
           bandwidth for this physical interface.";
      }
      container insight {
        description
          "InSight capability";
        leaf insight-enable {
          description
            "Enable InSight feature";
          type empty;
        }
        leaf insight-mmId {
          description
            "Management Module Id";
          type uint8 {
            range "1..2";
          }
        }
      }
    }
    list management {
      max-elements "1024";
      key "name";
      description
        "The list of management interfaces in the managed 
         device. Each row represents a management interface.";
      leaf name {
        type standalone-man-interface-type;
        description
          "The name of the management interface.";
      }
      container tcp {
        description
          "The TCP burstrate.";
        leaf tcp_burstrate {
          type uint32 {
            range "1..100000";
          }
          description
            "To enable tcp connection burstrate.";
        }
        leaf tcp_lockdown {
          type uint32 {
            range "5..3000";
          }
          default "5";
          description
            "To enable tcp connection lockdown time.";
        }
      }
      container ip {
        description
          "The IPv4 configurations for this management 
           interface.";
        container icmp {
          description
            "The ICMP control for this management interface.";
          leaf rate_limiting {
            type uint32 {
              range "0..4294967295";
            }
            default "1000";
            description
              "To enable ICMP incoming packet response rate limiting";
          }
        }
        container address {
          description
            "The IPv4 address configuration for this 
             management interface.";
          leaf dhcp {
            type empty;
            description
              "This specifies if DHCP is enabled or not.
               The presence of this leaf indicates that 
               this interface is configured for DHCP.";
          }
          leaf ip-address {
            type common-def:ipv4-address-prefix-type;
            description
              "This specifies the IP address for this 
               management interface.";
          }
        }
        container oper-address {
          leaf oper-ip-address {
            type common-def:ipv4-address-prefix-type;
            config false;
            description
              "The assigned IPv4 address.";
          }
        }
        container oper-gateway-con {
          leaf oper-gateway {
            type inet:ipv4-address;
            config false;
            description
              "The assigned gateway address.";
          }
        }
      }
      container ipv6 {
        description
          "The IPv6 configurations for this management 
           interface.";
        container icmpv6 {
          description
            "The ICMPv6 control for this management interface.";
          leaf v6_rate_limiting {
            type uint32 {
              range "0..4294967295";
            }
            default "1000";
            description
              "To enable ICMPv6 incoming rate limiting";
          }
        }
        container ipv6-address-cont {
          description
            "The IPv6 address configuration for this 
             management interface.";
          container ipv6-global-cont {
            leaf ipv6-global-address {
              type common-def:ipv6-address-prefix;
              description
                "IPv6 global address for this management 
                 interface.";
            }
            leaf ipv6-global-address-eui64 {
              type empty;
            }
          }
        }
        leaf-list ipv6-address {
          type string;
          config false;
          description
            "The list of IPv6 addresses assigned for this 
             management interface.";
        }
        leaf-list ipv6-gateways {
          type string;
          config false;
          description
            "The list of IPv6 gateways assigned for this 
             management interface.";
        }
      }
      container vrf {
        leaf vrf-forwarding {
          type common-def:vrf-name;
          description
            "This specifies the VRF that needs to be associated
             with interface.";
        }
      }
      leaf speed {
        type enumeration {
          enum "auto" {
            value 0;
            description
              "Auto-negotiation.";
          }
          enum "10" {
            value 1;
            description
              "10 Mbps Full Duplex";
          }
          enum "100" {
            value 2;
            description
              "100 Mbps Full Duplex";
          }
        }
        default "auto";
        description
          "This specifies the administratively configured
           bandwidth for this management interface.";
      }
      container line-speed {
        description
          "The line-speed characteristics for this management 
           interface.";
        leaf actual {
          config false;
          type string;
          description
            "The actual line-speed for this management 
             interface.";
        }
        leaf configured {
          config false;
          type string;
          description
            "The configured line-speed for this management 
             interface.";
        }
      }
      leaf shutdown_management {
        description
          "Shutdown this management interface.";
        type empty;
        mandatory false;
      }
      leaf shutdown_management_oper {
        description
          "Show the status of this management interface.";
        type string;
        config false;
      }
    }
  }

  grouping po-minimum-links-group {
    description
      "This specifies the minimum link group.";
    leaf minimum-links {
      type uint32 {
        range "1 .. 64";
      }
      default "1";
      description
        "The least number of operationally 'UP' links to 
         indicate port-channel being UP.";
    }
  }

  grouping interface-po-group {
    description
      "The interface level configurations to setup a 
       port-channel.";
    container channel-group {
      description
        "A container of configuration leaf elements for managing
         the channel-group membership.";
      leaf port-int {
        type portchannel-type;
        description
          "The port channel number.";
      }
      leaf mode {
        type po-mode;
        description
          "The mode of the port channel.";
      }
      leaf type {
        type po-type;
        description
          "The type of the port-channel.";
      }
    }
  }

  grouping allowed-vlan-add-group {
    description
      "A set of elements defining the vlan access policy.";
    container allowed {
      description
        "Set the VLANs that will Xmit/Rx through the Layer2
         interface";
      container vlan {
        leaf all {
          type empty;
          description
            "This is to specify all dot1q vlans or not.
             Presence of this leaf indicates all
             dot1q vlans are allowed.";
        }
        leaf none {
          type empty;
          description
            "This is to specify 'no dot1q vlans' or not. 
             Presence of this leaf indicates no dot1q
             vlans are allowed.";
        }
        leaf add {
          type ui32-vlan-20k-range;
          description
            "This specifies list of vlans to 
             be added.";
        }
        leaf except {
          type ui32-1k-vlan-range;
          description
            "This specifies exception list of 
             vlans.";
        }
        leaf remove {
          type ui32-1k-vlan-range;
          description
            "This specifies the list of vlans 
             to be removed.";
        }
      }
      container vlanoper {
        status deprecated;
        description
          "DEPRECATED
           NOS2.1.0 style data model for allowed vlans.
           Do not use in edit-config.";
        container vlan {
          leaf add {
            type ui32-vlan-range;
          }
          leaf remove {
            type ui32-vlan-range;
          }
        }
      }
    }
  }

  grouping interface-sw-trunk-rspan-group {
    description
      "Common grouping for the switchport trunk rspan commands";
    container rspan-vlan {
      description
        "configure a rspan-vlan";
      leaf add-rspan-trunk-vlan {
        type ui32-1k-vlan-range;
        description
          "Specify rspan-vlan id";
      }
      leaf remove-rspan-trunk-vlan {
        type ui32-1k-vlan-range;
        description
          "This specifies the list of rspan vlans to be removed.";
      }
    }
  }

  grouping interface-sw-access-rspan-group {
    description
      "Common grouping for the switchport access rspan commands";
    container rspan-access {
      description
        "The access layer characteristics of this 
         interface.";
      leaf rspan-access-vlan {
        type vlan-type;
        default "1";
        description
          "Specify rspan-vlan id to set as access vlan";
      }
    }
  }

  grouping secure-macs {
    description
      "List of secure MACs";
    list port-security-mac-address {
      description
        "Mac Address commands";
      key "mac-address port-sec-vlan";
      leaf mac-address {
        description
          "Mac Address";
        type mac-address-type;
      }
      leaf port-sec-vlan {
        description
          "Forwarding vlan";
        type vlan-type;
      }
    }
  }

  grouping interface-eth-po-group {
    description
      "The common grouping to characterize a physical/logical
       interface.";
    leaf mtu {
      type mtu-type;
      default "1548";
      description
        "The size of the largest packet which can be sent/
         received on the interface, specified in bytes.  
         For interfaces that are used for transmitting network
         datagrams, this is the size of the largest network 
         datagram that can be sent on the interface.";
    }
    leaf route-only {
      type empty;
      description
        "Configure port to route only L3 packets and drop all L2 switching packets.";
    }
    container switchport-basic {
      leaf basic {
        type empty;
      }
    }
    container switchport {
      description
        "The L2 switching characteristics of an interface.";
      container mode {
        description
          "The mode of the Layer2 interface.";
        leaf vlan-mode {
          type l2-mode-type;
          description
            "The access/trunk mode of this interface.";
        }
      }
      container port-security {
        presence "true";
        description
          "Enable port-security feature";
        leaf port-sec-max {
          description
            "Maximum number of allowed MACs";
          type uint32 {
            range "0..8192";
          }
        }
        leaf port-sec-violation {
          type port-sec-violation;
          description
            "Set the action on violation";
        }
        uses secure-macs;
        container sticky {
          description
            "Sticky MAC";
          leaf sticky-flag {
            description
              "Sticky Flag";
            type empty;
          }
          uses secure-macs;
        }
        leaf shutdown-time {
          type uint32 {
            range "1..15";
          }
          description
            "Shutdown time for port";
        }
      }
      container access {
        description
          "The access layer characteristics of this 
           interface.";
        leaf accessvlan {
          type vlan-type;
          description
            "This specifies the access vlan for this 
             interface.";
        }
      }
      container trunk {
        description
          "The trunking characteristics of this interface.";
        uses allowed-vlan-add-group;
        container tag {
          presence "tag";
          description
            "This specifies vlan tagging characteristics for a 
             trunk port.";
          leaf native-vlan {
            type empty;
            description
              "This specifies if the native vlan should be used 
               for classifying the un-tagged traffic.";
          }
        }
        container native-vlan-classification {
          leaf native-vlan-id {
            type native-vlan-type;
            description
              "The native vlan for an interface.";
          }
        }
      }
    }
  }

  grouping common-interface-group {
    leaf ifindex {
      config false;
      type uint64;
    }
    leaf description {
      type string {
        length "1 .. 63";
      }
    }
    leaf shutdown {
      type empty;
    }
  }

  grouping common-interface-group-vlan {
    leaf ifindex {
      config false;
      type uint64;
    }
    leaf description {
      type string {
        length "1 .. 63";
      }
    }
    leaf vlan-name {
      type string {
        length "1 .. 32";
      }
    }
  }

  grouping interface-ipv6 {
    container ipv6 {
      description
        "The IPv6 configurations for an interface.";
    }
  }

  grouping interface-ip {
    container ip {
      description
        "The IP configurations for an interface.";
    }
  }

  grouping bfd-interface-params-config {
    container bfd {
      description
        "Create BFD session on this interface.";
      container interval {
        description
          "Configure BFD desired min transmit interval in milliseconds.";
        leaf min-tx {
          type bfd-tx-interval-type;
          description
            "Configure BFD desired min transmit interval in milliseconds.";
        }
        leaf min-rx {
          type bfd-rx-interval-type;
          description
            "Configure BFD required min receive interval in milliseconds.";
        }
        leaf multiplier {
          type bfd-multiplier-type;
          description
            "Configure BFD detection time multiplier.";
        }
      }
      leaf bfd-shutdown {
        type empty;
        description
          "Administratively shutdown the BFD session.";
      }
    }
  }

  grouping tunable-optics-interface-cmds {
    container tunable-optics {
      container sfpp {
        leaf channel {
          type tunable-optics-sfpp-channel-type;
        }
      }
    }
  }

  augment "/interface/ethernet" {
    uses common-interface-group;
    uses interface-po-group;
    uses interface-eth-po-group;
    uses interface-ip;
    uses interface-vrf-config;
    uses interface-ipv6;
    uses bfd-interface-params-config;
    container vepa {
      leaf vepa-enable {
        type empty;
      }
    }
    container edge-loop-detection-native {
      leaf loop-detection-native {
        type empty;
      }
    }
    container edge-loop-detection {
      leaf eldprio {
        type uint32 {
          range "0..256";
        }
        default "128";
      }
      leaf eldshutdown-disable {
        type empty;
      }
      leaf eldvlan {
        type ui32-vlan-range;
      }
    }
    leaf priority-tag-enable {
      when "(/cap:capabilities/cap:l2/cap:port_profile = \"true\")";
      type empty;
    }
  }
  augment "/interface-vlan/vlan" {
    uses common-interface-group-vlan;
    container ip {
      description
        "The IP configurations for an interface.";
    }
  }
  augment "/interface/port-channel" {
    uses common-interface-group;
    uses po-minimum-links-group;
    uses interface-eth-po-group;
    uses interface-ip;
    uses interface-ipv6;
    container edge-loop-detection-native {
      leaf loop-detection-native {
        type empty;
      }
    }
    container edge-loop-detection {
      description
        "Enable edge-loop-detection on the selected interface";
      leaf eldprio {
        description
          "Set eld-priority value to interface";
        type uint32 {
          range "0..256";
        }
        default "128";
      }
      leaf eldshutdown-disable {
        type empty;
      }
      leaf eldvlan {
        description
          "Enable for specific VLAN on selected interface";
        type ui32-vlan-range;
      }
    }
    leaf priority-tag-enable {
      when "(/cap:capabilities/cap:l2/cap:port_profile = \"true\")";
      type empty;
    }
    leaf load-balance-type {
      type enumeration {
        enum "hash-based" {
          value 1;
        }
      }
      default "hash-based";
    }
  }
  augment "/interface/ethernet/switchport/trunk/allowed" {
    when "(/cap:capabilities/cap:l2/cap:rspan = \"true\")";
    uses interface-sw-trunk-rspan-group;
  }
  augment "/interface/ethernet/switchport/access" {
    when "(/cap:capabilities/cap:l2/cap:rspan = \"true\")";
    uses interface-sw-access-rspan-group;
  }
  augment "/interface/ethernet" {
    uses tunable-optics-interface-cmds;
  }
  augment "/common-def:routing-system" {
    container protocol {
      description
        "Protocol configuration.";
    }
    container interface {
      list ve {
        key "name";
        leaf name {
          type ve-type;
        }
        uses bfd-interface-params-config;
      }
    }
  }
}
