/*********************************************************************
 * Copyright (c) 2011 by Brocade Communications Systems, Inc.
 * All rights reserved.

 * brocade-ha.yang:Brocade HA Data model
 *
 * October,2011
 *
 *
 ********************************************************************/
module brocade-ha {
  namespace "urn:brocade.com:mgmt:brocade-ha";
  prefix ha;

  import tailf-common {
    prefix tailf;
  }
  import brocade-common-def {
    prefix common-def;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "This management module is an instrumentation to ha
     level commands";

  revision 2011-10-31 {
    description
      "Initial version of this management module.";
  }

  container ha {
    description
      "Configuration related to high availability functionalities.";
    container process-restart {
      leaf mpls {
        type empty;
      }
      leaf bgp {
        type empty;
      }
      leaf isis {
        type empty;
      }
      leaf ospfv2 {
        type empty;
      }
      leaf ospfv3 {
        type empty;
      }
    }
  }
  container ha-action {
    container ha {
      tailf:action "enable" {
        input {
          leaf force {
            type empty;
            mandatory false;
          }
        }
      }
      tailf:action "disable" {
        input {
          leaf force {
            type empty;
            mandatory false;
          }
        }
      }
      tailf:action "dump" {
        input;
      }
      tailf:action "chassisreboot" {
        input;
      }
      tailf:action "failover" {
        input {
          leaf force {
            type empty;
            mandatory false;
          }
        }
      }
      container sync {
        tailf:action "start" {
          input;
          output {
            leaf result {
              type string;
            }
          }
        }
        tailf:action "stop" {
          input;
          output {
            leaf result {
              type string;
            }
          }
        }
      }
    }
  }
  augment "/common-def:show" {
    container ha {
      tailf:action "ha" {
        input {
          leaf all-partitions {
            type empty;
            mandatory false;
          }
        }
      }
    }
  }
  augment "/common-def:show" {
    container redundancy {
      tailf:action "redundancy";
    }
  }
  container system-ha {
    tailf:action "reload" {
      input {
        leaf system {
          type empty;
          mandatory false;
        }
        leaf standby {
          type empty;
          mandatory false;
        }
      }
      output {
        leaf status-string {
          description
            "Command status in string format";
          type string;
          mandatory false;
        }
      }
    }
  }
  rpc reload {
    input {
      leaf system {
        type empty;
        mandatory false;
      }
      leaf standby {
        type empty;
        mandatory false;
      }
    }
  }
}
