/*********************************************************************
 * Copyright (c) 2011 by Brocade Communications Systems, Inc.
 * All rights reserved.
 * brocade-system: Brocade  Data Model
 *
 * August 2011, Jaykishan Leelakrishnan 
 *
 *
 ********************************************************************/
module brocade-system-watermark {
  namespace "urn:brocade.com:mgmt:brocade-system-watermark";
  prefix system-watermark;

  organization "Brocade Communications Systems, Inc.";
  contact
    "Brocade Communications Systems, Inc.
     Postal: 130 Holger Way
     San Jose, CA 95134
     U.S.A
     Tel: +1-408-333-6061
     E-mail: support@Brocade.com
     web: www.brocade.com.";
  description
    "This module defines SYSTEM related information.";

  revision 2011-08-09 {
    description
      "Added new get system uptime interface for netconf.";
  }

  container system-config {
    container interface {
      leaf utilization-watermark {
        type empty;
      }
    }
  }
}
