/*********************************************************************
 * Copyright (c) 2011 by Brocade Communications Systems, Inc.
 * All rights reserved.
 * brocade-vcs.yang: Brocade VCS Cluster Data Model
 *
 * April 2011, Brian Adaniya, Sanjeev C Joshi
 *
 *
 ********************************************************************/
module brocade-vcs {
  namespace "urn:brocade.com:mgmt:brocade-vcs";
  prefix vcs;

  import ietf-yang-types {
    prefix yang;
  }

  organization "Brocade Communications Systems, Inc.";
  contact
    "Brocade Communications Systems, Inc.
     Postal: 130 Holger Way
             San Jose, CA 95134
              U.S.A
     Tel: +1-408-333-8000
     E-mail: support@Brocade.com 
     web: www.brocade.com.";
  description
    "This management module is an instrumentation to manage  
     Virtual Cluster Switching (VCS).
             
     Glossary of the terms used:
     --------------------------- 
     VAL  - Virtual Access Layer, provided by VCS.
     VCS  - Virtual Cluster Switching.
     TRILL - Transparent Interconnection of Lot of Links.
     TLS - Transparent LAN Services.
             
             
     VCS refers to the ability of a group of physical Ethernet 
     switches, inter-connected in arbitrary fashion via the regular 
     front-end data ports, to present themselves as one unified and
     transparent Ethernet switching service to the external network. 
     The inter-connecting network that glues all these individual 
     switches is refered as 'fabric', and the group of physical 
     Ethernet switches in the fabric is refered to as 'cluster'. 
             
     +--------+                                   +--------+
     |External|                                   |External| 
     |Non-VCS |                                   |Non-VCS |
     |Switch  |                                   |Switch  |
     +--------+                                   +--------+          
       |                                              |
       |                                              |
       |                                              |
     +---+                                            |          
     |   |                                            | 
     |S1 |                                      ******************
     +---+                                      * Logical Switch *  
       |<------ Fabric Port    \\---->           *                *  
       |                       /---->           * (VCS Cluster)  *
     +---+                                      ******************
     |   |                                            |
     |S2 |                                            |
     +---+                                            |
       |<----- Edge Port                              |
       |                                              |
     +-------+                                   +-------+
     |Server |                                   |Server |
     +-------+                                   +-------+
     
     [Physical View]                            [Logical View]
     
     As shown in the figure above, the fabric ports are transparent 
     as far as the external devices connected to the VCS are 
     concerned. In this sense the whole of the cluster behaves like 
     a logical switch to the external network.         
    ";

  revision 2011-05-26 {
    description
      "Initial version of this management module.";
  }

  container vcsmode {
    config false;
    leaf vcs-mode {
      type boolean;
      mandatory true;
    }
    leaf vcs-cluster-mode {
      type boolean;
      mandatory true;
    }
  }
  container local-node {
    config false;
    leaf swbd-number {
      type uint32;
      mandatory true;
    }
  }
  rpc get-last-config-update-time {
    description
      "This rpc function provides time-stamp of the last 
       configutation change done on the managed device.";
    output {
      leaf last-config-update-time {
        type uint64;
        description
          "This leaf indicates the time-stamp of the last 
           configuration change on the system.";
      }
    }
  }
  rpc get-last-config-update-time-for-xpaths {
    input {
      list xpath-strings {
        key "xpath-string";
        leaf xpath-string {
          type string;
        }
      }
    }
    output {
      list last-config-update-time-for-xpaths {
        key "xpath-string";
        leaf xpath-string {
          type string;
        }
        leaf last-config-update-time {
          type uint64;
        }
      }
    }
  }
}
