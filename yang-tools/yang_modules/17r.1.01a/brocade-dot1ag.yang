/*********************************************************************
 * Copyright (c) 2011 by Brocade Communications Systems, Inc.
 * All rights reserved.
 * brocade-dot1ag.yang: Brocade CFM Module
 *
 *
 *
 ********************************************************************/
module brocade-dot1ag {
  namespace "urn:brocade.com:mgmt:brocade-dot1ag";
  prefix dot1ag;

  import brocade-interface {
    prefix interface;
  }

  organization "Brocade Communications Systems, Inc.";
  contact
    "Brocade Communications Systems, Inc.
     Postal: 130 Holger Way,
             San Jose, CA 95134
              U.S.A
     Tel: +1-408-333-8000
     E-mail: support@Brocade.com
     web: www.brocade.com.";
  description
    "This management module is an instrumentation to manage
     CFM Protocol.";

  revision 2014-01-03 {
    description
      "Initial version of this management module.";
  }

  typedef mip-policy-type {
    type enumeration {
      enum "default" {
        value 1;
      }
      enum "explicit" {
        value 2;
      }
    }
  }

  typedef mep-down-up-type {
    type enumeration {
      enum "down" {
        value 1;
      }
      enum "up" {
        value 2;
      }
    }
  }

  typedef ccm-tlv-type {
    type enumeration {
      enum "port-status-tlv" {
        value 1;
      }
    }
  }

  typedef ccm-interval-type {
    type enumeration {
      enum "3.3-ms" {
        value 1;
      }
      enum "10-ms" {
        value 2;
      }
      enum "100-ms" {
        value 3;
      }
      enum "1-second" {
        value 4;
      }
      enum "10-seconds" {
        value 5;
      }
    }
  }

  typedef dot1ag-interface-type {
    type enumeration {
      enum "ethernet" {
        value 1;
      }
      enum "port-channel" {
        value 2;
      }
    }
  }

  typedef dot1ag-interface-name {
    type string {
      pattern "((([0-9]|[1][0-6])/([1-9]|[1-9][0-9]|[1-9][0-9][0-9])(:[1-4])?)|([0-9]([0-9])?([0-9])?([0-9])?))";
      length "1..16";
    }
  }

  typedef maid-format-type {
    type enumeration {
      enum "default" {
        value 0;
      }
      enum "long" {
        value 1;
      }
    }
  }

  typedef y1731-profile-type {
    type enumeration {
      enum "delay-measurement" {
        value 1;
      }
      enum "synthetic-loss-measurement" {
        value 2;
      }
    }
  }

  typedef y1731-profile-tx-interval {
    type enumeration {
      enum "1-second" {
        value 1;
      }
      enum "10-seconds" {
        value 2;
      }
      enum "60-seconds" {
        value 3;
      }
      enum "600-seconds" {
        value 4;
      }
    }
  }

  typedef y1731-profile-mode {
    type enumeration {
      enum "initiator" {
        value 1;
      }
      enum "responder" {
        value 2;
      }
    }
  }

  typedef y1731-start-periodic {
    type enumeration {
      enum "daily" {
        value 1;
      }
    }
  }

  typedef time-in-hhmmss {
    type string {
      pattern "([0-1][0-9]|[2][0-3]){1}(:[0-5][0-9]){2}";
    }
  }

  typedef schedule-type {
    type enumeration {
      enum "at" {
        value 1;
      }
      enum "after" {
        value 2;
      }
    }
  }

  typedef action-profile-bitmap {
    type bits {
      bit interface-down {
        position 0;
      }
      bit event-handler {
        position 1;
      }
      bit all {
        position 15;
      }
    }
  }

  augment "/interface:protocol" {
    container cfm {
      presence "true";
      container y1731 {
        presence "true";
        list test-profile {
          key "test-profile";
          leaf test-profile {
            type string {
              length "1..32";
            }
          }
          leaf profile-type {
            type y1731-profile-type;
          }
          container test-profile-params {
            when "../profile-type";
            leaf tx-interval {
              type y1731-profile-tx-interval;
              default "1-second";
            }
            leaf measurement-interval {
              type uint32 {
                range "1..1440";
              }
              default "15";
            }
            leaf cos {
              type uint8 {
                range "0..8";
              }
              default "7";
            }
            leaf tx-frame-count {
              type uint32 {
                range "1..1000";
              }
              default "10";
            }
            leaf timeout {
              type uint8 {
                range "1..4";
              }
              default "1";
            }
            container start {
              leaf start-type {
                type schedule-type;
              }
              leaf start-time {
                type time-in-hhmmss;
              }
              leaf start-periodic {
                type y1731-start-periodic;
              }
            }
            container stop {
              leaf stop-type {
                type schedule-type;
              }
              leaf stop-time {
                type time-in-hhmmss;
              }
            }
            container slm-threshold {
              when "../../profile-type = 'synthetic-loss-measurement'";
              container forward {
                leaf thr-fwd-avg-value {
                  type uint32 {
                    range "1..4294967295";
                  }
                  default "4294967295";
                }
                leaf thr-fwd-max-value {
                  type uint32 {
                    range "1..4294967295";
                  }
                  default "4294967295";
                }
              }
              container backward {
                leaf thr-bwd-avg-value {
                  type uint32 {
                    range "1..4294967295";
                  }
                  default "4294967295";
                }
                leaf thr-bwd-max-value {
                  type uint32 {
                    range "1..4294967295";
                  }
                  default "4294967295";
                }
              }
            }
            container dmm-threshold {
              when "../../profile-type = 'delay-measurement'";
              leaf thr-avg-value {
                type uint32 {
                  range "1..4294967295";
                }
                default "4294967295";
              }
              leaf thr-max-value {
                type uint32 {
                  range "1..4294967295";
                }
                default "4294967295";
              }
            }
          }
        }
        list action-profile-name {
          key "action-profile-name";
          leaf action-profile-name {
            type string {
              length "1..32";
            }
          }
          container event {
            container ccm-up {
              leaf ccm-up-actions {
                type action-profile-bitmap;
                default "";
              }
            }
            container ccm-down {
              leaf ccm-down-actions {
                type action-profile-bitmap;
                default "";
              }
            }
            container avg-threshold {
              leaf avg-threshold-actions {
                type action-profile-bitmap;
                default "";
              }
            }
            container max-threshold {
              leaf max-threshold-actions {
                type action-profile-bitmap;
                default "";
              }
            }
          }
        }
      }
      list domain-name {
        key "domain-name";
        leaf domain-name {
          type string {
            length "1..21";
          }
        }
        leaf domain-level {
          type uint32 {
            range "0..7";
          }
          mandatory true;
        }
        list ma-name {
          key "ma-name";
          leaf ma-name {
            type string {
              length "1..21";
            }
          }
          leaf ma-id {
            mandatory true;
            type uint32 {
              range "1..4090";
            }
          }
          choice vid-type {
            case vlan {
              leaf ma-vlan-vid {
                type uint32 {
                  range "1..4090";
                }
              }
            }
            case bridgeDomain {
              leaf ma-bd-vid {
                type uint32 {
                  range "1..16384";
                }
              }
            }
          }
          leaf ma-priority {
            type uint32 {
              range "0..7";
            }
          }
          container cfm-ma-sub-commands {
            leaf ccm-interval {
              type ccm-interval-type;
            }
            leaf mip-policy {
              type mip-policy-type;
            }
            leaf maid-format {
              type maid-format-type;
            }
            uses cfm-config-cmds-mep-attributes;
          }
        }
      }
    }
  }

  grouping cfm-config-cmds-mep-attributes {
    list mep {
      key "mep-id";
      leaf mep-id {
        type uint32 {
          range "1..8191";
        }
      }
      leaf mep-down-up {
        mandatory true;
        type mep-down-up-type;
      }
      leaf vlan {
        type uint32 {
          range "1..4090";
        }
      }
      leaf inner-vlan {
        type uint32 {
          range "1..4090";
        }
      }
      leaf mep-intf-type {
        type dot1ag-interface-type;
      }
      leaf mep-intf-name {
        type dot1ag-interface-name;
      }
      container cfm-mep-sub-commands {
        leaf tlv-type {
          type ccm-tlv-type;
        }
        list remote-mep {
          key "remote-mep";
          leaf remote-mep {
            type uint32 {
              range "1..8191";
            }
          }
          list rmep-test-profile {
            key "rmep-test-profile mode";
            leaf rmep-test-profile {
              type string {
                length "1..32";
              }
            }
            leaf mode {
              type y1731-profile-mode;
            }
          }
          leaf action-profile-association {
            type string {
              length "1..32";
            }
          }
        }
      }
    }
  }
}
