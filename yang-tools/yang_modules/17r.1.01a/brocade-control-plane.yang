/*********************************************************
 * Copyright (c) 2016 by Brocade Communications Systems, Inc.
 * All rights reserved.
 * Brocade Control Plane Data model
 *
 * May 2016, Sajad Bashir Qadri
 *
 *
 **********************************************************/
module brocade-control-plane {
  namespace "urn:brocade.com:mgmt:brocade-control-plane";
  prefix control-plane;

  organization "Brocade Communications Systems, Inc.";
  contact
    "Brocade Communications Systems, Inc.
     Postal: 130 Holger Way
             San Jose, CA 95134
             U.S.A
     Tel: +1-408-333-8000
     E-mail: support@Brocade.com
     web: www.brocade.com.";
  description
    "This management module is an instrumentation to control-plane
     level commands";

  revision 2016-04-30 {
    description
      "Initial version of this management module.";
  }

  typedef rate-limit-cir {
    type uint32 {
      range "0 .. 100000";
    }
    units "kbps - kilobits per second";
  }

  typedef rate-limit-cbr {
    type uint32 {
      range "1 .. 64";
    }
    units "kilobytes";
  }

  grouping subnet_rate_limit {
    container subnet-rate-limit {
      leaf cir {
        type rate-limit-cir;
      }
      leaf cbr {
        type rate-limit-cbr;
      }
    }
  }

  container control-plane {
    container ipv6 {
      uses subnet_rate_limit;
    }
  }
}
