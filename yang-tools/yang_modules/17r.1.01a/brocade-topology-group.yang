/*********************************************************************
 * Copyright (c) 2015 by Brocade Communications Systems, Inc.
 * All rights reserved.
 *brocade-topology-group.yang: Brocade topology group module data model
 *
 * Apr 2015, Sri Harsha Nadella
 *
 *
 ********************************************************************/
module brocade-topology-group {
  namespace "urn:brocade.com:mgmt:brocade-topology-group";
  prefix topology-group;

  import brocade-bridge-domain {
    prefix bd;
  }

  organization "Brocade Communications Systems, Inc.";
  contact
    "Brocade Communications Systems, Inc.
     Postal: 130 Holger Way
             San Jose, CA 95134
             U.S.A
     Tel: +1-408-333-8000
     E-mail: support@Brocade.com
     web: www.brocade.com.";
  description
    "This submodule Manages Topology Group related CLI.";

  revision 2015-09-04 {
    description
      "Initial Version of Topology Group module.";
  }

  typedef ui32-member-vlan-range {
    type string {
      pattern "((1[0-9]{1,2})|([2-9][0-9]{0,2})|([1-3][0-9]{3})|(40[0-8][0-9])|(4090))(-((1[0-9]{1,2})|([2-9][0-9]{0,2})|([1-3][0-9]{3})|(40[0-8][0-9])|(4090)))?((,((1[0-9]{1,2})|([2-9][0-9]{0,2})|([1-3][0-9]{3})|(40[0-8][0-9])|(4090))(-((1[0-9]{1,2})|([2-9][0-9]{0,2})|([1-3][0-9]{3})|(40[0-8][0-9])|(4090)))?)?)*";
      length "1..253";
    }
    description
      "The definition for specifying the member-vlan range.";
  }

  list topology-group {
    key "topology-group-id";
    leaf topology-group-id {
      type uint32 {
        range "1..128";
      }
    }
    leaf master-vlan {
      type uint32 {
        range "2..4090";
      }
    }
    container member-vlan {
      when "../master-vlan != 0";
      leaf member-vlan-add {
        type ui32-member-vlan-range;
        description
          "This specifies list of Member VLANs to
           be added to this topology group";
      }
      leaf member-vlan-remove {
        type ui32-member-vlan-range;
        description
          "This specifies list of Member VLANs to
           be removed from this topology group";
      }
    }
    container member-bridge-domain {
      when "../master-vlan != 0";
      leaf member-bridge-domain-add {
        type bd:ui32-bridge-domain-range;
        description
          "This specifies list of Member Bridge Domains to
           be added to this topology group";
      }
      leaf member-bridge-domain-remove {
        type bd:ui32-bridge-domain-range;
        description
          "This specifies list of Member Bridge Domains to
           be removed from this topology group";
      }
    }
  }
}
