/*********************************************************************
 * Copyright (c) 2011 by Brocade Communications Systems, Inc.
 * All rights reserved.
 * brocade-aaa-ext.yang-: Brocade aaa-show-users Data Model
 *
 * April 2011, Newton Oku 
 *
 *
 ********************************************************************/
module brocade-aaa-ext {
  namespace "urn:brocade.com:mgmt:brocade-aaa-ext";
  prefix aaa-extensions;

  import tailf-common {
    prefix tailf;
  }
  import brocade-common-def {
    prefix common-def;
  }

  revision 2010-09-21 {
    description
      "Added aaa-show-ext.";
  }

  augment "/common-def:show" {
    container aaa-users {
      tailf:action "users" {
        input;
      }
    }
  }
  rpc user-session-info {
    output {
      leaf user-role {
        type string {
          length "4 .. 32";
        }
      }
    }
  }
}
