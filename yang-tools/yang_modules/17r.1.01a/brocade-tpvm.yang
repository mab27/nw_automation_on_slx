/*********************************************************************
 * Copyright (c) 2016 by Brocade Communications Systems, Inc.
 * All rights reserved.
 * brocade-tpvm.yang:Brocade TPVM Data model
 *
 * October, 2016, Eiji Ota
 *
 *
 ********************************************************************/
module brocade-tpvm {
  namespace "urn:brocade.com:mgmt:brocade-tpvm";
  prefix tpvm;

  import tailf-common {
    prefix tailf;
  }

  organization "Brocade Communications Systems, Inc.";
  contact
    "Brocade Communications Systems, Inc.
     Postal: 130 Holger Way
           San Jose, CA 95134
     U.S.A
     Tel: +1-408-333-8000
     E-mail: support@Brocade.com
     web: www.brocade.com.";
  description
    "This management module is an instrumentation to TPVM
                   administration commands";

  revision 2016-10-14 {
    description
      "initial version of this management module.";
  }

  typedef bladeType {
    type string {
      pattern "MM1|MM2";
      length "3";
    }
    description
      "blade name";
  }

  typedef diskName {
    type string {
      pattern "vd[b-x]";
      length "3..4";
    }
  }

  typedef diskSize {
    type string {
      pattern "[1-9][0-9]*|[1-9][0-9]*[bkmg]";
      length "1..256";
    }
  }

  container tpvm {
    tailf:action "install" {
      input {
        leaf blade {
          type bladeType;
          mandatory false;
        }
        leaf debug {
          type boolean;
          default "false";
          mandatory false;
        }
      }
      output {
        leaf tpvm-install-msg {
          type string;
        }
      }
    }
    tailf:action "uninstall" {
      input {
        leaf force {
          type empty;
          mandatory false;
          description
            "clear errors forcefully";
        }
        leaf blade {
          type bladeType;
          mandatory false;
        }
        leaf debug {
          type boolean;
          default "false";
          mandatory false;
        }
      }
      output {
        leaf tpvm-uninstall-msg {
          type string;
        }
      }
    }
    tailf:action "password" {
      input {
        leaf blade {
          type bladeType;
          mandatory false;
        }
        leaf debug {
          type boolean;
          default "false";
          mandatory false;
        }
      }
      output {
        leaf tpvm-update-password-msg {
          type string;
        }
      }
    }
    tailf:action "start" {
      input {
        leaf blade {
          type bladeType;
          mandatory false;
        }
        leaf debug {
          type boolean;
          default "false";
          mandatory false;
        }
      }
      output {
        leaf tpvm-start-msg {
          type string;
        }
      }
    }
    tailf:action "stop" {
      input {
        leaf blade {
          type bladeType;
          mandatory false;
        }
        leaf debug {
          type boolean;
          default "false";
          mandatory false;
        }
      }
      output {
        leaf tpvm-stop-msg {
          type string;
        }
      }
    }
    container auto-boot {
      tailf:action "enable" {
        input {
          leaf blade {
            type bladeType;
            mandatory false;
          }
          leaf debug {
            type boolean;
            default "false";
            mandatory false;
          }
        }
        output {
          leaf tpvm-enable-on-boot-msg {
            type string;
          }
        }
      }
      tailf:action "disable" {
        input {
          leaf blade {
            type bladeType;
            mandatory false;
          }
          leaf debug {
            type boolean;
            default "false";
            mandatory false;
          }
        }
        output {
          leaf tpvm-disable-on-boot-msg {
            type string;
          }
        }
      }
    }
    container show {
      tailf:action "status" {
        input {
          leaf debug {
            type boolean;
            default "false";
            mandatory false;
          }
          leaf clear-tag {
            type string {
              length "1..256";
            }
            description
              "clear tag";
            mandatory false;
          }
          leaf blade {
            type bladeType;
            mandatory false;
          }
        }
        output {
          leaf tpvm-status-msg {
            type string;
          }
        }
      }
      tailf:action "ip-address" {
        input {
          leaf blade {
            type bladeType;
            mandatory false;
          }
          leaf debug {
            type boolean;
            default "false";
            mandatory false;
          }
        }
        output {
          leaf tpvm-ipaddr-msg {
            type string;
          }
        }
      }
      tailf:action "disk" {
        input {
          leaf name {
            type union {
              type diskName;
              type string {
                pattern "all";
              }
            }
            mandatory true;
            description
              "disk name";
          }
          leaf blade {
            type bladeType;
            mandatory false;
          }
          leaf debug {
            type boolean;
            default "false";
            mandatory false;
          }
        }
        output {
          leaf tpvm-show-disk-msg {
            type string;
          }
        }
      }
    }
    container disk {
      tailf:action "add" {
        input {
          leaf name {
            type union {
              type diskName;
              type string {
                pattern "auto";
              }
            }
            mandatory true;
            description
              "disk name";
          }
          leaf size {
            type diskSize;
            mandatory true;
            description
              "disk size";
          }
          leaf blade {
            type bladeType;
            mandatory false;
          }
          leaf debug {
            type boolean;
            default "false";
            mandatory false;
          }
        }
        output {
          leaf tpvm-add-disk-msg {
            type string;
          }
        }
      }
      tailf:action "remove" {
        input {
          leaf name {
            type union {
              type diskName;
              type string {
                pattern "auto";
              }
            }
            mandatory true;
            description
              "disk name";
          }
          leaf blade {
            type bladeType;
            mandatory false;
          }
          leaf debug {
            type boolean;
            default "false";
            mandatory false;
          }
        }
        output {
          leaf tpvm-remove-disk-msg {
            type string;
          }
        }
      }
    }
  }
}
