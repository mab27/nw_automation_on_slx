/*********************************************************************
 * Copyright (c) 2011 by Brocade Communications Systems, Inc.
 * All rights reserved.
 * brocade-distributedlog.yang: Brocade Distributedlog Data Model
 *
 * April 2011, Jaykishan Leelakrishnan
 *
 *
 ********************************************************************/
module brocade-distributedlog {
  namespace "urn:brocade.com:mgmt:brocade-distributedlog";
  prefix distributedlog;

  import tailf-common {
    prefix tailf;
  }
  import brocade-common-def {
    prefix common-def;
  }

  organization "Brocade Communications Inc.";
  contact
    "Brocade Communications Systems, Inc.
     Postal: 130 Holger Way,
     San Jose, CA 95134
     U.S.A
     Tel: +1-408-333-8000
     E-mail: support@Brocade.com
     web: www.brocade.com.";
  description
    "Vcs log related information";
  reference "<Author Name>, '<Title>', <RFC XXXX>, <Month> <YEAR>.";

  revision 2010-12-02 {
    description
      "Initial version";
  }

  augment "/common-def:show" {
    container log {
      tailf:action "audit" {
        input {
          choice audit-log-input {
            mandatory true;
            case non-support-save-logs {
              leaf non-support-save {
                type empty;
              }
            }
            case all-logs {
              leaf all {
                type empty;
              }
            }
            case filtered-logs {
              leaf user {
                type string;
              }
              leaf type {
                type enumeration {
                  enum "session";
                  enum "command";
                }
              }
            }
          }
          leaf limit {
            type uint32;
          }
        }
      }
    }
  }
}
