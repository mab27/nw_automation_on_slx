/*******************************************************************
 * Copyright (c) 2011 by Brocade Communications Systems, Inc.        *
 * All rights reserved.                                              *
 * brocade-sflow.yang: Brocade SFLOW  module data model                      *
 *                                                                   *
 * March 2011, Venkat                                                *
 *                                                                   *
 *                                                                   *
 *******************************************************************/
module brocade-sflow {
  namespace "urn:brocade.com:mgmt:brocade-sflow";
  prefix sflow;

  import ietf-inet-types {
    prefix inet;
  }
  import brocade-common-def {
    prefix common-def;
  }
  import brocade-interface {
    prefix interface;
  }
  import brocade-sec-services {
    prefix source-interface-common;
  }

  organization "Brocade Communications";
  contact
    "Brocade Communications Systems, Inc.
     Postal: 130 Holger Way
             San Jose, CA 95134
             U.S.A
     Tel: +1-408-333-8000
     E-mail: support@Brocade.com
     web: www.brocade.com.";
  description
    "This submodule describes the data model for sFlow";

  revision 2009-12-10 {
    description
      "Initial Version";
  }

  grouping sflow-config {
    leaf polling-interval {
      default "20";
      type uint32 {
        range "0..65535";
      }
    }
    leaf sample-rate {
      default "2048";
      type uint32 {
        range "1..100000";
      }
    }
  }

  grouping common-phy-sflow-cmds {
    container sflow {
      leaf enable {
        type empty;
      }
      uses sflow-config;
    }
  }

  typedef profile-name-type {
    type string {
      pattern "[a-zA-Z]{1}([-a-zA-Z0-9_]{0,63})";
    }
  }

  container sflow {
    leaf enable {
      type empty;
    }
    container source-interface {
      uses source-interface-common:source-interface-name-group;
    }
    list collector {
      key "collector-ip-address collector-port-number use-vrf";
      leaf collector-ip-address {
        type inet:ip-address;
      }
      leaf collector-port-number {
        type uint32 {
          range "1..65535";
        }
      }
      leaf use-vrf {
        type common-def:vrf-name;
      }
    }
    uses sflow-config;
  }
  augment "/interface:interface/interface:ethernet" {
    uses common-phy-sflow-cmds;
  }
}
