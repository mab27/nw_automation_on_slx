/*********************************************************************
 * Copyright (c) 2010 by Brocade Communications Systems, Inc.
 * All rights reserved.
 * brocade-aaa.yang: Brocade AAA module data model
 *
 * November, 2010, Charanjith Reddy Kunduru
 *
 *
 ********************************************************************/
module brocade-aaa {
  namespace "urn:brocade.com:mgmt:brocade-aaa";
  prefix brcd-aaa;

  import tailf-common {
    prefix tailf;
  }
  import brocade-common-def {
    prefix common-def;
  }
  import brocade-interface {
    prefix interface;
  }
  import brocade-intf-loopback {
    prefix loopback-intf;
  }

  organization "Brocade Communications Systems, Inc.";
  contact
    "Address :    120 Holger Way
                San Jose, CA 95134
                U.S.A
     Phone     :    +1-408-333-8000
     E-mail     :  support@brocade.com
     Website     :  www.brocade.com";
  description
    "Data Model for AAA CLIs";

  revision 2010-10-21 {
    description
      "Removed the max-elements attribute for list";
  }

  typedef auth-protocols {
    type enumeration {
      enum "chap" {
        value 0;
      }
      enum "pap" {
        value 1;
      }
      enum "peap-mschap" {
        value 2;
      }
    }
  }

  typedef rad-auth-protocols {
    type auth-protocols;
  }

  typedef tac-protocols {
    type enumeration {
      enum "chap" {
        value 0;
      }
      enum "pap" {
        value 1;
      }
    }
  }

  typedef tac-auth-protocols {
    type tac-protocols;
  }

  typedef tac-auth-port {
    type uint16 {
      range "1 .. 65535";
    }
  }

  typedef srcip_type {
    type enumeration {
      enum "chassis-ip" {
        value 1;
      }
      enum "mm-ip" {
        value 2;
      }
    }
  }

  typedef rad-auth-port {
    type uint16 {
      range "1 .. 65535";
    }
  }

  typedef ldap-auth-port {
    type uint16 {
      range "1 .. 65535";
    }
  }

  typedef user-passwd {
    type string {
      length "8..40";
    }
  }

  typedef username-enable {
    type boolean;
  }

  typedef action {
    type enumeration {
      enum "accept";
      enum "reject";
    }
  }

  typedef rule-action {
    type action;
  }

  typedef operation {
    type enumeration {
      enum "read-only";
      enum "read-write";
    }
  }

  typedef rule-operation {
    type operation;
  }

  typedef acc_srv_type {
    type enumeration {
      enum "none" {
        value 0;
      }
      enum "radius" {
        value 1;
      }
      enum "tacacs+" {
        value 2;
      }
    }
  }

  typedef mm-iftype {
    type string {
      pattern "([0-1])";
    }
  }

  typedef ve-iftype {
    type string {
      pattern "([1-9]|[1-9][0-9]|[1-9][0-9][0-9]|[1-3][0-9][0-9][0-9]|4[0][0-9][0-6])";
    }
  }

  typedef loopback-iftype {
    type string {
      pattern "([1-9]|[1-9][0-9]|1[0-9][0-9]|2[0-4][0-9]|25[0-5])";
    }
  }

  typedef track-iftype {
    type enumeration {
      enum "ethernet" {
        value 1;
        description
          "Ethernet interface";
      }
      enum "loopback" {
        value 2;
        description
          "loopback interface";
      }
      enum "ve" {
        value 3;
        description
          "ve interface";
      }
      enum "management" {
        value 4;
      }
    }
  }

  typedef date {
    type string {
      length "0 .. 10";
      pattern "((19(0[2-9]|[1-9][0-9])|20([012][0-9]|3[0-7]))-(0[1-9]|1[012])-(0[1-9]|[12][0-9]|3[01]))|never" {
        error-message "Expiry date should be in the range 1902 and 2037, or 'never'(no expiry)";
      }
    }
  }

  typedef root_access_type {
    type enumeration {
      enum "console" {
        value 1;
      }
    }
  }

  container aaa-config {
    container aaa {
      container authentication {
        container login {
          leaf first {
            type enumeration {
              enum "default" {
                value 0;
              }
              enum "radius" {
                value 1;
              }
              enum "tacacs+" {
                value 2;
              }
              enum "ldap" {
                value 3;
              }
              enum "local" {
                value 4;
              }
            }
          }
          leaf second {
            type enumeration {
              enum "local" {
                value 4;
              }
              enum "local-auth-fallback" {
                value 5;
              }
            }
          }
        }
      }
      container accounting {
        container exec {
          container defaultacc {
            container start-stop {
              leaf server-type {
                type acc_srv_type;
              }
            }
          }
        }
        container commands {
          container defaultacc {
            container start-stop {
              leaf server-type {
                type acc_srv_type;
              }
            }
          }
        }
      }
    }
  }
  list username {
    key "name";
    leaf name {
      type string {
        length "1 .. 40" {
          error-message
            "User name length should be in the
             range 1-40";
        }
      }
    }
    leaf user-password {
      type user-passwd;
      mandatory true;
    }
    leaf encryption-level {
      type enumeration {
        enum "0" {
          value 0;
        }
        enum "7" {
          value 7;
        }
      }
    }
    leaf role {
      type string {
        length "4 .. 32" {
          error-message
            "Role name length should be in the
             range 4-32";
        }
      }
      mandatory true;
    }
    leaf desc {
      type string {
        length "0 .. 64" {
          error-message
            "Account description length should be
             in the range 0-64";
        }
      }
      default "";
    }
    leaf enable {
      type username-enable;
      default "true";
    }
    leaf expire {
      type date;
      default "never";
    }
    leaf access-time {
      type string;
      default "";
    }
    leaf end-time {
      type string;
      default "";
    }
  }
  container service {
    leaf password-encryption {
      type empty;
    }
  }
  container user {
    tailf:action "unlock" {
      input {
        leaf username {
          type string {
            length "1 .. 40" {
              error-message
                "The existing user name length
                 should be in the range 1-40";
            }
          }
          mandatory true;
        }
      }
      output {
        leaf Result {
          type string {
            length "0..max";
          }
        }
      }
    }
  }
  container role {
    list name {
      key "name";
      leaf name {
        type string {
          length "4 .. 32" {
            error-message
              "Role name should be in the range
               4-32";
          }
        }
      }
      leaf desc {
        type string {
          length "0 .. 64" {
            error-message
              "Role description should be in the
               range 0-64";
          }
        }
        default "";
      }
    }
  }
  container radius-server {
    list host {
      key "hostname use-vrf";
      leaf hostname {
        type string {
          length "0..max";
          pattern "\\p{IsBasicLatin}{0,255}";
        }
      }
      leaf use-vrf {
        type common-def:vrf-name;
      }
      container radius-server-options {
        leaf auth-port {
          type rad-auth-port;
          default "1812";
        }
        leaf protocol {
          type rad-auth-protocols;
          default "chap";
        }
        leaf key {
          type string {
            length "8 .. max";
          }
        }
        leaf encryption-level {
          type enumeration {
            enum "0" {
              value 0;
            }
            enum "7" {
              value 7;
            }
          }
        }
        leaf retries {
          type uint32 {
            range "0 .. 100" {
              error-message
                "Retries must be in the
                 range 0 - 100";
            }
          }
          default "5";
        }
        leaf timeout {
          type uint32 {
            range "1 .. 60" {
              error-message
                "Timeout must be in the range
                 1 - 60";
            }
          }
          default "5";
        }
        container source-interface {
          leaf source-interface-name {
            type track-iftype;
          }
          leaf source-interface-value {
            type union {
              type interface:interface-type;
              type loopback-iftype;
              type ve-iftype;
              type mm-iftype;
            }
          }
        }
      }
    }
  }
  container tacacs-server {
    list host {
      key "hostname use-vrf";
      leaf hostname {
        type string {
          length "0..max";
          pattern "\\p{IsBasicLatin}{0,255}";
        }
      }
      leaf use-vrf {
        type common-def:vrf-name;
      }
      container tacacs-server-options {
        leaf port {
          type tac-auth-port;
          default "49";
        }
        leaf protocol {
          type tac-auth-protocols;
          default "chap";
        }
        leaf key {
          type string {
            length "1 .. max";
          }
        }
        leaf encryption-level {
          type enumeration {
            enum "0" {
              value 0;
            }
            enum "7" {
              value 7;
            }
          }
        }
        leaf retries {
          type uint8 {
            range "0 .. 100" {
              error-message
                "Retries must be in the range
                 0 - 100";
            }
          }
          default "5";
        }
        leaf timeout {
          type uint8 {
            range "1 .. 60" {
              error-message
                "Timeout must be in the range
                 1 - 60";
            }
          }
          default "5";
        }
      }
    }
    leaf tacacs-source-ip {
      type srcip_type;
      default "mm-ip";
    }
  }
  container ldap-server {
    list host {
      key "hostname use-vrf";
      leaf hostname {
        type string {
          length "1..max";
          pattern "\\p{IsBasicLatin}{0,255}";
        }
      }
      leaf use-vrf {
        type common-def:vrf-name;
      }
      container ldap-server-options {
        leaf port {
          type ldap-auth-port;
          default "389";
        }
        leaf retries {
          type uint8 {
            range "0 .. 100" {
              error-message
                "Retries must be in the range
                 0 - 100";
            }
          }
          default "5";
        }
        leaf timeout {
          type uint8 {
            range "1 .. 60" {
              error-message
                "Timeout must be in the range
                 1 - 60";
            }
          }
          default "5";
        }
        leaf basedn {
          type string {
            length "1..255";
          }
          default "local";
        }
      }
    }
    container maprole {
      list group {
        key "ad-group";
        leaf ad-group {
          type string {
            length "1..max";
          }
        }
        leaf switch-role {
          type string {
            length "4 .. 32" {
              error-message
                "Role name should be in the range
                 4-32";
            }
          }
          mandatory true;
        }
      }
    }
  }
  container password-attributes {
    leaf min-length {
      type uint32 {
        range "8 .. 32" {
          error-message
            "Password minimum length should be in
             the range 8-32";
        }
      }
      default "8";
    }
    leaf max-retry {
      type uint32 {
        range "0 .. 16" {
          error-message
            "Maximum login retries value should
             be in the range 0-16";
        }
      }
      default "0";
    }
    leaf max-lockout-duration {
      type uint32 {
        range "0 .. 99999" {
          error-message
            "Maximum lockout duration value should
             be in the range 0-99999";
        }
      }
      default "0";
    }
    container character-restriction {
      leaf upper {
        type uint32 {
          range "0 .. 32" {
            error-message
              "Minimum number of upper-case
               alphabets should be in the range 0-32";
          }
        }
        default "0";
      }
      leaf lower {
        type uint32 {
          range "0 .. 32" {
            error-message
              "Minimum number of lower-case
               alphabets should be in the range 0-32";
          }
        }
        default "0";
      }
      leaf numeric {
        type uint32 {
          range "0 .. 32" {
            error-message
              "Minimum number of numeric
               characters should be in the range 0-32";
          }
        }
        default "0";
      }
      leaf special-char {
        type uint32 {
          range "0 .. 32" {
            error-message
              "Minimum number of special
               characters should be in the range 0-32";
          }
        }
        default "0";
      }
    }
    leaf admin-lockout-enable {
      type empty;
    }
  }
  container banner {
    leaf login {
      type string {
        length "0..2048";
      }
      default "";
    }
    leaf motd {
      type string {
        length "0..2048";
      }
      default "";
    }
    leaf incoming {
      type string {
        length "0..2048";
      }
      default "";
    }
  }

  grouping cmdstructure {
    container command {
      choice cmdlist {
        case container-cmds {
          leaf enumList {
            type enumeration {
              enum "dot1x";
              enum "mac-address-table";
              enum "cidrecov";
              enum "vlan";
              enum "qos";
              enum "mac";
              enum "sflow";
              enum "monitor";
              enum "system-monitor";
              enum "telnet";
              enum "ssh";
              enum "aaa";
              enum "radius-server";
              enum "tacacs-server";
              enum "ldap-server";
              enum "password-attributes";
              enum "username";
              enum "role";
              enum "banner";
              enum "rule";
              enum "alias-config";
              enum "snmp-server";
              enum "clock";
              enum "ntp";
              enum "filter-change-update-delay";
              enum "license";
              enum "configure";
              enum "support";
              enum "logging";
              enum "firmware";
              enum "dir";
              enum "df";
              enum "prompt1";
              enum "prompt2";
              enum "delete";
              enum "rename";
              enum "terminal";
              enum "ip" {
                value 48;
              }
              enum "ipv6";
              enum "protocol";
              enum "lacp";
              enum "switch-attributes" {
                value 55;
              }
              enum "vrf";
              enum "reload";
              enum "usb";
              enum "rmon";
              enum "fastboot";
              enum "unlock";
              enum "debug";
              enum "service";
              enum "no-operation";
              enum "python";
            }
          }
        }
        case interface-a {
          container interface-int {
            container interface-cont {
              presence "true";
            }
          }
        }
        case interface-c {
          container interface-eth {
            container interface {
              container ethernet-cont {
                presence "true";
              }
            }
          }
        }
        case interface-e {
          container interface-eth-leaf {
            container interface {
              leaf ethernet-leaf {
                type interface:interface-type;
              }
            }
          }
        }
        case interface-f {
          container interface-mgmt {
            container interface {
              container management-cont {
                presence "true";
              }
            }
          }
        }
        case interface-i {
          container interface-pc {
            container interface {
              container port-channel-cont {
                presence "true";
              }
            }
          }
        }
        case interface-j {
          container interface-pc-leaf {
            container interface {
              leaf port-channel-leaf {
                type interface:portchannel-type;
              }
            }
          }
        }
        case interface-m {
          container interface-management-leaf {
            container interface {
              leaf management-leaf {
                type interface:man-interface-type;
              }
            }
          }
        }
        case interface-n {
          container interface-loopback {
            container interface {
              container loopback-cont {
                presence "true";
              }
            }
          }
        }
        case interface-o {
          container interface-loopback-leaf {
            container interface {
              leaf loopback-leaf {
                type loopback-intf:intf-loopback-port-type;
              }
            }
          }
        }
        case interface-p {
          container interface-ve {
            container interface {
              container ve-cont {
                presence "true";
              }
            }
          }
        }
        case interface-q {
          container interface-ve-leaf {
            container interface {
              leaf ve-leaf {
                type interface:ve-type;
              }
            }
          }
        }
        case copy-a {
          container copy-cp {
            container copy-cont {
              presence "true";
            }
          }
        }
        case copy-b {
          container copy-running {
            container copy {
              container running-config-cont {
                presence "true";
              }
            }
          }
        }
        case copy-c {
          container copy-support {
            container copy {
              container support-cp {
                presence "true";
              }
            }
          }
        }
        case clear-a {
          container clear-cl {
            container clear-cont {
              presence "true";
            }
          }
        }
        case clear-b {
          container clear-logging {
            container clear {
              container logging-cont {
                presence "true";
              }
            }
          }
        }
        case clear-c {
          container clear-support {
            container clear {
              container support-cl {
                presence "true";
              }
            }
          }
        }
        case protocol-a {
          container protocol-pr {
            container protocol-cont {
              presence "true";
            }
          }
        }
        case protocol-b {
          container protocol-spanning {
            container protocol {
              container spanning-tree-cont {
                presence "true";
              }
            }
          }
        }
        case protocol-c {
          container protocol-lldp {
            container protocol {
              container lldp-cont {
                presence "true";
              }
            }
          }
        }
      }
    }
  }

  list rule {
    key "index";
    leaf index {
      type uint32 {
        range "1 .. 512";
      }
    }
    leaf action {
      type rule-action;
    }
    leaf operation {
      type rule-operation;
    }
    leaf role {
      type string {
        length "4 .. 32" {
          error-message
            "Role name length should be in the
             range 4-32";
        }
      }
    }
    uses cmdstructure;
  }

  grouping root-group {
    container root {
      leaf enable {
        type empty;
      }
      leaf access {
        type root_access_type;
      }
    }
  }

  container root-sa {
    uses root-group;
  }
  container alias-config {
    list alias {
      key "name";
      leaf name {
        type string {
          length "1..255" {
            error-message
              "Alias name length should be
               in the range 1-255";
          }
        }
      }
      leaf expansion {
        type string {
          length "1..1023" {
            error-message
              "Alias expansion length should be
               in the range 1-1023";
          }
        }
        mandatory true;
      }
    }
    list user {
      key "name";
      leaf name {
        type string {
          length "1..40" {
            error-message
              "User name length should be
               in the range 1-40";
          }
        }
      }
      list alias {
        key "name";
        leaf name {
          type string {
            length "1..255" {
              error-message
                "Alias name length should be
                 in the range 1-255";
            }
          }
        }
        leaf expansion {
          type string {
            length "1..1023" {
              error-message
                "Alias expansion length should be
                 in the range 1-1023";
            }
          }
          mandatory true;
        }
      }
    }
  }
  augment "/common-def:clear" {
    container login {
      tailf:action "sessions" {
        description
          "Logout the user sessions in the switch";
        input;
        output;
      }
    }
  }
}
