/*********************************************************************
 * Copyright (c) 2011 by Brocade Communications Systems, Inc.
 * All rights reserved.
 * brocade-mct.yang: Brocade Mct data model
 *
 *
 *
 ********************************************************************/
module brocade-mct {
  namespace "urn:brocade.com:mgmt:brocade-mct";
  prefix mct;

  import brocade-common-def {
    prefix common-def;
  }
  import ietf-inet-types {
    prefix inet;
  }

  organization "Brocade Communications Systems, Inc.";
  contact
    "Brocade Communications Systems, Inc.
     Postal: 130 Holger Way,
             San Jose, CA 95134
              U.S.A
     Tel: +1-408-333-8000
     E-mail: support@Brocade.com
     web: www.brocade.com.";
  description
    "This management module is an instrumentation to manage Mct .";

  revision 2011-06-21 {
    description
      "Initial version of this management module
       brocade-mct.";
  }

  typedef string-type {
    type string {
      length "1..10";
    }
  }

  typedef peer-ifname {
    type string {
      pattern "(((([1-9]|[1-9][0-9]|1[0-9]{2}|2[0-3][0-9])/)?(([0-9]|1[0-6]))/([1-9]|[1-9][0-9])(:[1-4])?)|([1-9]|[1-9][0-9]|[1-9][0-9]{2}|[1-7][0-9]{3}|8[0-1][0-9][0-1]))";
    }
  }

  typedef cluster-client-esi {
    type string {
      pattern "([0-9a-fA-F]{1,2}(:[0-9a-fA-F]{1,2}){2,8})(;[0-9a-fA-F]{1,2}(:[0-9a-fA-F]{1,2}){2,8})*" {
        description
          "";
      }
    }
    description
      "Cluster client ESI";
  }

  typedef ui32-vlan-range {
    type string {
      pattern "(([1-9][0-9]{0,2})|([1-3][0-9]{3})|(40[0-8][0-9])|(4090))(-((1[0-9]{1,2})|([1-9][0-9]{0,2})|([1-3][0-9]{3})|(40[0-8][0-9])|(4090)))?((,((1[0-9]{1,2})|([2-9][0-9]{0,2})|([1-3][0-9]{3})|(40[0-8][0-9])|(4090))(-((1[0-9]{1,2})|([1-9][0-9]{0,2})|([1-3][0-9]{3})|(40[0-8][0-9])|(4090)))?)?)*";
      length "1..253";
    }
    description
      "The definition for specifying the vlan range.";
  }

  typedef ui32-bd-range {
    type string {
      pattern "(([1-9][0-9]{0,2})|([1-3][0-9]{3})|(40[0-8][0-9])|(409[0-6]))(-((1[0-9]{1,2})|([1-9][0-9]{0,2})|([1-3][0-9]{3})|(40[0-8][0-9])|(409[0-6])))?((,((1[0-9]{1,2})|([2-9][0-9]{0,2})|([1-3][0-9]{3})|(40[0-8][0-9])|(409[0-6]))(-((1[0-9]{1,2})|([1-9][0-9]{0,2})|([1-3][0-9]{3})|(40[0-8][0-9])|(409[0-6])))?)?)*";
      length "1..253";
    }
    description
      "The definition for specifying the BD range.";
  }

  list cluster {
    max-elements "1";
    key "cluster-name cluster-id";
    leaf cluster-name {
      type common-def:name-string64;
      description
        "Name for the Cluster (MAX: 64 Characters)";
    }
    leaf cluster-id {
      type uint32 {
        range "1..65535";
      }
    }
    container member {
      container vlan {
        description
          "Member vlan's part of the  MCT .";
        leaf add {
          type ui32-vlan-range;
          description
            "This specifies list of vlans to
             be added to MCT.";
        }
        leaf remove {
          type ui32-vlan-range;
          description
            "This specifies the list of vlans
             to be removed.";
        }
      }
      container bridge-domain {
        description
          "Member BD's part of the  MCT .";
        leaf add-bd {
          type ui32-bd-range;
          description
            "This specifies list of BDs to
             be added to MCT.";
        }
        leaf remove-bd {
          type ui32-bd-range;
          description
            "This specifies the list of BDs
             to be removed.";
        }
      }
    }
    container peer-interface {
      leaf peer-if-type {
        type enumeration {
          enum "Ethernet" {
            value 8;
          }
          enum "Ve" {
            value 4;
            description
              "Ve interface";
          }
        }
      }
      leaf peer-if-name {
        type peer-ifname;
      }
    }
    list peer {
      max-elements "1";
      key "peer-ip";
      leaf peer-ip {
        type inet:ipv4-address;
      }
    }
    leaf client-interfaces-shutdown {
      type empty;
    }
    container client-isolation {
      leaf strict {
        type empty;
      }
      leaf loose {
        type empty;
      }
    }
    leaf designated-forwarder-hold-time {
      type uint16 {
        range "1..60";
      }
    }
    leaf deploy {
      type empty;
    }
    list client {
      max-elements "512";
      key "client-name client-id";
      leaf client-name {
        type string {
          length "1..64";
        }
      }
      leaf client-id {
        type uint32 {
          range "1..512";
        }
      }
      container client-interface {
        leaf if-type {
          type enumeration {
            enum "Ethernet" {
              value 8;
            }
            enum "Port-channel" {
              value 3;
            }
          }
        }
        leaf if-value {
          type string-type;
        }
      }
      leaf esi {
        description
          "Cluster client ESI";
        type cluster-client-esi;
      }
      leaf client-deploy {
        type empty;
      }
    }
    container client-pw {
      description
        "Client Pseudo Wire";
      presence "true";
      leaf client-pw-esi {
        description
          "Cluster client-pw ESI";
        type cluster-client-esi;
      }
      leaf client-pw-deploy {
        type empty;
      }
    }
  }
}
