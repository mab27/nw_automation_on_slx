/*********************************************************************
 * Copyright (c) 2013 by Brocade Communications Systems, Inc.
 * All rights reserved.
 * brocade-bfd.yang
 *      Brocade BFD(Bidirectional Forwarding Detection) management module
 *
 * Sep 2014
 *
 *
 ********************************************************************/
module brocade-bfd {
  namespace "urn:brocade.com:mgmt:brocade-bfd";
  prefix bfd;

  organization "Brocade Communications Systems, Inc.";
  contact
    "Brocade Communications Systems, Inc.
     Postal: 130 Holger Way
             San Jose, CA 95134
             U.S.A   
     Tel: +1-408-333-8000
     E-mail: support@Brocade.com
     Web: www.brocade.com";
  description
    "This management module is an instrumentation to manage BFD.";

  revision 2014-09-24 {
    description
      "Added common typedefs for BFD config.";
  }

  typedef bfd-tx-interval-type {
    type uint32 {
      range "50..30000";
    }
    units "milliseconds";
  }

  typedef bfd-rx-interval-type {
    type uint32 {
      range "50..30000";
    }
    units "milliseconds";
  }

  typedef bfd-multiplier-type {
    type uint32 {
      range "3..50";
    }
  }

  typedef bfd-holdover-interval {
    type uint32 {
      range "1..30";
    }
    units "seconds";
  }

  grouping bfd-interval {
    container interval {
      description
        "Configure BFD desired min transmit interval in milliseconds.";
      leaf min-tx {
        type bfd-tx-interval-type;
        description
          "Configure BFD desired min transmit interval in milliseconds.";
      }
      leaf min-rx {
        type bfd-rx-interval-type;
        description
          "Configure BFD required min receive interval in milliseconds.";
      }
      leaf multiplier {
        type bfd-multiplier-type;
        description
          "Configure BFD detection time multiplier.";
      }
    }
  }
}
