/*********************************************************************
 * Copyright (c) 2010-2013 by Brocade Communications Systems, Inc.
 * All rights reserved.
 * brocade-firmware.yang:Brocade Firmware Data model
 *
 * April 2011,Aditya Munjal
 *
 *
 ********************************************************************/
module brocade-firmware {
  namespace "urn:brocade.com:mgmt:brocade-firmware";
  prefix firmware;

  import tailf-common {
    prefix tailf;
  }
  import brocade-common-def {
    prefix common-def;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "This management module is an instrumentation to firmware level
     level commands";

  revision 2011-04-11 {
    description
      "Initial version of this management module.";
  }

  grouping fwdl-parameters {
    leaf user {
      type string;
      mandatory true;
    }
    leaf password {
      type string;
      mandatory false;
    }
    leaf host {
      type string;
      mandatory true;
    }
    leaf directory {
      type string;
      mandatory true;
    }
    leaf file {
      type string;
      mandatory false;
    }
  }

  grouping tftp_fwdl-parameters {
    leaf host {
      type string;
      mandatory true;
    }
    leaf directory {
      type string;
      mandatory true;
    }
    leaf file {
      type string;
      mandatory false;
    }
  }

  grouping fwdl-local-options {
    choice options {
      case manual {
        leaf manual {
          type empty;
          mandatory false;
        }
        leaf noreboot {
          type empty;
          mandatory false;
        }
        leaf nocommit {
          type empty;
          mandatory false;
        }
      }
      case noactivate {
        leaf noactivate {
          type empty;
          mandatory false;
        }
      }
      case coldboot {
        leaf coldboot {
          type empty;
          mandatory false;
        }
      }
    }
  }

  grouping fwdl-default-config-options {
    leaf manual {
      type empty;
      mandatory false;
    }
    leaf noreboot {
      type empty;
      mandatory false;
    }
  }

  grouping fwdl-output {
    leaf fwdl-tid {
      type int32;
    }
    leaf fwdl-status {
      type int32;
    }
    leaf fwdl-msg {
      type string;
    }
  }

  grouping fwdl-cluster-output {
    leaf fwdl-cmd-status {
      type int32;
    }
    leaf fwdl-cmd-msg {
      type string;
    }
    list cluster-output {
      leaf fwdl-status {
        type int32;
      }
      leaf fwdl-msg {
        type string;
      }
    }
  }

  grouping fwdl-sftp-options {
    leaf port {
      type int32;
      mandatory false;
    }
    leaf host-key-check {
      type empty;
      mandatory false;
    }
  }

  grouping firmware-clean-install-config {
    leaf manual {
      type empty;
      mandatory false;
    }
  }

  grouping fwdl-fullinstall-options {
    leaf manual {
      type empty;
      mandatory false;
    }
  }

  grouping fwdl-inband-options {
    leaf use-vrf {
      type common-def:vrf-name;
      mandatory false;
    }
  }

  container firmware {
    container download {
      tailf:action "ftp" {
        input {
          uses fwdl-parameters;
          uses fwdl-local-options;
          uses fwdl-inband-options;
        }
        output {
          uses fwdl-output;
        }
      }
      tailf:action "scp" {
        input {
          uses fwdl-parameters;
          uses fwdl-local-options;
          uses fwdl-inband-options;
        }
        output {
          uses fwdl-output;
        }
      }
      tailf:action "tftp" {
        input {
          uses tftp_fwdl-parameters;
          uses fwdl-local-options;
        }
        output {
          uses fwdl-output;
        }
      }
      tailf:action "sftp" {
        input {
          uses fwdl-parameters;
          uses fwdl-local-options;
          uses fwdl-sftp-options;
          uses fwdl-inband-options;
        }
        output {
          uses fwdl-output;
        }
      }
      tailf:action "usb" {
        input {
          leaf directory {
            type string;
            mandatory true;
          }
          uses fwdl-local-options;
        }
        output {
          uses fwdl-output;
        }
      }
      tailf:action "interactive" {
        input;
        output {
          leaf result {
            type string;
          }
        }
      }
      container default-config {
        tailf:action "ftp" {
          input {
            uses fwdl-parameters;
            uses fwdl-default-config-options;
            uses fwdl-inband-options;
          }
          output {
            uses fwdl-output;
          }
        }
        tailf:action "scp" {
          input {
            uses fwdl-parameters;
            uses fwdl-default-config-options;
            uses fwdl-inband-options;
          }
          output {
            uses fwdl-output;
          }
        }
        tailf:action "sftp" {
          input {
            uses fwdl-parameters;
            uses fwdl-default-config-options;
            uses fwdl-inband-options;
          }
          output {
            uses fwdl-output;
          }
        }
        tailf:action "tftp" {
          input {
            uses tftp_fwdl-parameters;
            uses fwdl-default-config-options;
          }
          output {
            uses fwdl-output;
          }
        }
        tailf:action "usb" {
          input {
            leaf directory {
              type string;
              mandatory true;
            }
            uses fwdl-default-config-options;
          }
          output {
            uses fwdl-output;
          }
        }
      }
      container fullinstall {
        tailf:action "ftp" {
          input {
            uses fwdl-parameters;
            uses fwdl-fullinstall-options;
            uses fwdl-inband-options;
          }
          output {
            uses fwdl-output;
          }
        }
        tailf:action "scp" {
          input {
            uses fwdl-parameters;
            uses fwdl-fullinstall-options;
            uses fwdl-inband-options;
          }
          output {
            uses fwdl-output;
          }
        }
        tailf:action "sftp" {
          input {
            uses fwdl-parameters;
            uses fwdl-fullinstall-options;
            uses fwdl-inband-options;
          }
          output {
            uses fwdl-output;
          }
        }
        tailf:action "tftp" {
          input {
            uses tftp_fwdl-parameters;
            uses fwdl-fullinstall-options;
          }
          output {
            uses fwdl-output;
          }
        }
        tailf:action "usb" {
          input {
            leaf directory {
              type string;
              mandatory true;
            }
            uses fwdl-fullinstall-options;
          }
          output {
            uses fwdl-output;
          }
        }
      }
    }
    container install {
      tailf:action "ftp" {
        input {
          uses fwdl-parameters;
          uses firmware-clean-install-config;
          uses fwdl-inband-options;
        }
        output {
          uses fwdl-output;
        }
      }
      tailf:action "scp" {
        input {
          uses fwdl-parameters;
          uses firmware-clean-install-config;
          uses fwdl-inband-options;
        }
        output {
          uses fwdl-output;
        }
      }
    }
    tailf:action "commit" {
      input;
      output {
        leaf result {
          type string;
        }
      }
    }
    tailf:action "restore" {
      input;
      output {
        leaf result {
          type string;
        }
      }
    }
    tailf:action "sync" {
      input;
      output {
        leaf result {
          type string;
        }
      }
    }
    tailf:action "activate" {
      input;
      output {
        leaf overall-status {
          type int32;
        }
        leaf overall-error-msg {
          type string;
        }
        leaf status {
          type int32;
        }
      }
    }
    tailf:action "recover" {
      input;
      output {
        leaf result {
          type string;
        }
      }
    }
    container auto-sync {
      tailf:action "enable" {
        input;
        output {
          leaf result {
            type string;
          }
        }
      }
      tailf:action "disable" {
        input;
        output {
          leaf result {
            type string;
          }
        }
      }
    }
    container peripheral-update-option {
      tailf:action "peripheral-update-cpld";
      tailf:action "peripheral-update-fpga";
      container peripheral-update-bmc-option {
        tailf:action "peripheral-update-bmc-all";
        tailf:action "peripheral-update-bmc-boot";
        tailf:action "peripheral-update-bmc-application";
      }
    }
  }
  container write {
    tailf:action "erase" {
      input;
      output {
        uses fwdl-output;
      }
    }
  }
  rpc fwdl-status {
    input {
      leaf fwdl-tid {
        type int32;
      }
    }
    output {
      leaf number-of-entries {
        type uint32;
      }
      leaf fwdl-state {
        type enumeration {
          enum "in-progress" {
            value 1;
          }
          enum "downloaded" {
            value 2;
          }
          enum "failed" {
            value 3;
          }
          enum "completed" {
            value 4;
          }
        }
      }
      list fwdl-entries {
        leaf index {
          type uint32;
        }
        leaf message-id {
          type int32;
        }
        leaf date-and-time-info {
          type string;
        }
        leaf message {
          type string;
        }
        leaf blade-slot {
          type int32;
        }
        leaf blade-swbd {
          type int32;
        }
        leaf blade-name {
          type string;
        }
        leaf blade-state {
          type enumeration {
            enum "active" {
              value 0;
            }
            enum "standby" {
              value 1;
            }
          }
        }
        leaf blade-app {
          type string;
        }
      }
    }
  }
  rpc activate-status {
    output {
      leaf overall-status {
        type int32;
      }
      leaf overall-error-msg {
        type string;
      }
      leaf status {
        type int32;
      }
    }
  }
  rpc firmware-download {
    input {
      choice protocol-type {
        case scp-protocol {
          container scp {
            uses fwdl-parameters;
          }
        }
        case ftp-protocol {
          container ftp {
            uses fwdl-parameters;
          }
        }
        case sftp-protocol {
          container sftp {
            uses fwdl-parameters;
            uses fwdl-sftp-options;
          }
        }
        case usb-protocol {
          container usb {
            leaf directory {
              type string;
              mandatory true;
            }
          }
        }
      }
      leaf coldboot {
        type empty;
      }
    }
    output {
      uses fwdl-cluster-output;
    }
  }
  container reboot {
    tailf:action "fastboot" {
      input;
    }
  }
  container dhcp {
    container auto-deployment {
      tailf:action "enable" {
        input;
        output {
          leaf dad-cmd-msg {
            type string;
          }
        }
      }
    }
    container ztp {
      tailf:action "log" {
        input;
        output {
          leaf dad-cmd-msg {
            type string;
          }
        }
      }
      tailf:action "cancel" {
        input;
        output {
          leaf dad-cmd-msg {
            type string;
          }
        }
      }
    }
  }
  augment "/common-def:show" {
    container dhcp-auto-deployment {
      tailf:action "dadstatus" {
        input;
        output {
          leaf result {
            type string;
          }
        }
      }
    }
    container show-firmware-dummy {
      container show-firmware-option {
        container peripheral-show-option {
          tailf:action "peripheral-show-cpld";
          tailf:action "peripheral-show-fpga";
          container peripheral-show-bmc-option {
            tailf:action "peripheral-show-bmc-all";
            tailf:action "peripheral-show-bmc-boot";
            tailf:action "peripheral-show-bmc-application";
          }
        }
      }
    }
  }
  rpc dad-status {
    output {
      leaf dad-last-state {
        type enumeration {
          enum "dad-in-progress" {
            value 0;
          }
          enum "dad-failed" {
            value 1;
          }
          enum "dad-completed" {
            value 2;
          }
        }
      }
      list dad-status-entries {
        leaf index {
          type uint32;
        }
        leaf date-and-time-info {
          type string;
        }
        leaf message {
          type string;
        }
      }
    }
  }
}
