/*********************************************************************
 * Copyright (c) 2011 by Brocade Communications Systems, Inc.
 * All rights reserved.
 * brocade-ip-config.yang: Brocade IP Forwarding data model.
 *
 * jusitnh
 *
 *
 ********************************************************************/
module brocade-ip-config {
  namespace "urn:brocade.com:mgmt:brocade-ip-config";
  prefix ip-config;

  import brocade-interface {
    prefix interface;
  }
  import brocade-common-def {
    prefix common-def;
  }
  import brocade-intf-loopback {
    prefix intf-loopback;
  }
  import ietf-inet-types {
    prefix inet;
  }

  revision 2011-10-31 {
    description
      "Initial version of this management module.";
  }

  typedef ip-mtu {
    type uint32 {
      range "1300..9194";
    }
  }

  grouping phy-intf-ip-config {
    container ip-config {
      leaf mtu {
        type ip-mtu;
        default "1500";
      }
      leaf proxy-arp {
        type empty;
      }
      leaf arp-aging-timeout {
        type uint32 {
          range "0..240";
        }
        default "240";
      }
      list address {
        ordered-by user;
        key "address";
        leaf address {
          type union {
            type common-def:ipv4-prefix-mask;
            type inet:ipv4-prefix;
          }
        }
        leaf secondary {
          type empty;
        }
        leaf ospf-passive {
          type empty;
        }
        leaf ospf-ignore {
          type empty;
        }
      }
    }
  }

  grouping intf-vlan-ip-config {
    container ip-config {
      leaf mtu {
        type ip-mtu;
        default "1500";
      }
      leaf proxy-arp {
        type empty;
      }
      leaf arp-aging-timeout {
        type uint32 {
          range "0..240";
        }
        default "240";
        description
          "Set arp age timeout value to interface 
           (default value 240)";
      }
      list address {
        ordered-by user;
        key "address";
        leaf address {
          type union {
            type common-def:ipv4-prefix-mask;
            type inet:ipv4-prefix;
          }
        }
        leaf secondary {
          type empty;
        }
        leaf ospf-passive {
          type empty;
        }
        leaf ospf-ignore {
          type empty;
        }
      }
    }
  }

  grouping loopback-intf-ip-config {
    container ip-config {
      list address {
        key "address";
        leaf address {
          type union {
            type intf-loopback:intf-loopback-ipv4addr-type;
            type inet:ipv4-prefix;
          }
        }
      }
    }
  }

  augment "/interface:interface/interface:ethernet/interface:ip" {
    uses phy-intf-ip-config;
  }
  augment "/common-def:routing-system/interface:interface/intf-loopback:loopback" {
    container ip {
      uses loopback-intf-ip-config;
    }
  }
  augment "/common-def:routing-system/interface:interface/interface:ve" {
    uses interface:interface-vrf-config;
    container ip {
      uses intf-vlan-ip-config;
    }
    leaf shutdown {
      type empty;
    }
  }
}
