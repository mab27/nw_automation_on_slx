/*********************************************************************
 * Copyright (c) 2011 by Brocade Communications Systems, Inc.
 * All rights reserved.
 * brocade-system-monitor-ext.yang: data model for show system-monitor
 *
 * May 2011, Newton Oku
 *
 *
 ********************************************************************/
module brocade-system-monitor-ext {
  namespace "urn:brocade.com:mgmt:brocade-system-monitor-ext";
  prefix system-monitor-extensions;

  import tailf-common {
    prefix tailf;
  }
  import ietf-inet-types {
    prefix inet;
  }
  import ietf-yang-types {
    prefix ietfyang;
  }
  import brocade-common-def {
    prefix common-def;
  }

  organization "Brocade Communications Inc.";
  contact
    "Brocade Communications Systems, Inc.
     Postal: 130 Holger Way
             San Jose, CA 95134
             U.S.A
     Tel: +1-408-333-6061
     E-mail: support@Brocade.com
     web: www.brocade.com.";
  description
    "This sub module defines show system-monitor data model
     Copyright (c) 2011 by Brocade Communications Systems, Inc.
     All rights reserved.";

  revision 2011-05-05 {
    description
      "Initial version of this module.";
  }

  typedef system-monitor-health-state-enum {
    type enumeration {
      enum "state-unknown";
      enum "state-healthy";
      enum "state-marginal";
      enum "state-down";
      enum "state-unmonitored";
    }
  }

  typedef system-monitor-port-state-enum {
    type enumeration {
      enum "port-healthy";
      enum "port-marginal";
      enum "port-faulty";
      enum "port-offline";
    }
  }

  augment "/common-def:show" {
    container system {
      tailf:action "monitor" {
        output {
          list switch-status {
            leaf switch-name {
              type string;
            }
            leaf switch-ip {
              type inet:ip-address;
            }
            leaf report-time {
              type ietfyang:date-and-time;
            }
            leaf switch-state {
              type system-monitor-health-state-enum;
            }
            list component-status {
              leaf component-name {
                type string;
              }
              leaf component-state {
                type system-monitor-health-state-enum;
              }
            }
            list faulty-port {
              leaf port-name {
                type string;
              }
            }
          }
        }
      }
    }
  }
  rpc show-system-monitor {
    output {
      list switch-status {
        leaf switch-name {
          type string;
          description
            "name of the switch";
        }
        leaf switch-ip {
          type inet:ip-address;
          description
            "ip address of the switch";
        }
        leaf report-time {
          type ietfyang:date-and-time;
          description
            "switch report timestamp";
        }
        leaf switch-state {
          type system-monitor-health-state-enum;
          description
            "switch status based on components";
        }
        leaf switch-state-reason {
          type string;
          description
            "component reason for switch status";
        }
        list component-status {
          leaf component-name {
            type string;
            description
              "component name";
          }
          leaf component-state {
            type system-monitor-health-state-enum;
            description
              "component status based on thresholds";
          }
        }
        list port-status {
          leaf port-area {
            type uint32;
            description
              "port identifier";
          }
          leaf port-name {
            type string;
          }
          leaf port-state {
            type system-monitor-port-state-enum;
            description
              "port state";
          }
        }
      }
    }
  }
}
