/*********************************************************************
 * Copyright (c) 2014 by Brocade Communications Systems, Inc.
 * All rights reserved.
 * brocade-dhcpv6.yang: Brocade YANG data model for DHCPv6 configuration.
 *		 			  Currently supports basic relay agent functionality
 *					  only.
 *
 * June 2014, Sachin Rastogi
 *
 *
 ********************************************************************/
module brocade-dhcpv6 {
  namespace "urn:brocade.com:mgmt:brocade-dhcpv6";
  prefix dhcpv6;

  import brocade-interface {
    prefix interface;
  }
  import brocade-ipv6-config {
    prefix ipv6-config;
  }
  import brocade-common-def {
    prefix common-def;
  }
  import ietf-inet-types {
    prefix inet;
  }

  organization "Brocade Communications Systems, Inc.";
  contact
    "Brocade Communications Systems, Inc.
     Postal: 130 Holger Way,
             San Jose, CA 95134 
              U.S.A
     Tel: +1-408-333-8000
     E-mail: support@Brocade.com 
     web: www.brocade.com.";
  description
    "This management module is an instrumentation to manage 
     DHCPv6 functionality.";

  revision 2014-06-11 {
    description
      "Initial version of this management module.";
  }

  typedef dhcp-ipv6-address {
    type inet:ipv6-address;
  }

  typedef dhcpv6-iftype {
    type enumeration {
      enum "ethernet" {
        value 0;
        description
          "Ethernet interface";
      }
      enum "Ve" {
        value 4;
        description
          "Ve interface";
      }
    }
  }

  typedef dhcpv6-ifname {
    type string {
      pattern "(((([1-9]|[1-9][0-9]|1[0-9]{2}|2[0-3][0-9])/)?(([0-9]|1[0-6]))/([1-9]|[1-9][0-9])(:[1-4])?)|([1-9]|[1-9][0-9]|[1-9][0-9]{2}|[1-7][0-9]{3}|8[0-1][0-9][0-1]))";
    }
  }

  grouping interface-phy-dhcp {
    container interface-phy-dhcp-conf {
      uses interface-dhcp;
    }
  }

  grouping interface-ve-dhcp {
    container interface-ve-dhcp-conf {
      uses interface-dhcp;
    }
  }

  grouping interface-dhcp {
    container dhcp {
      container relay {
        list servers {
          key "relay-ip-addr";
          max-elements "16";
          leaf relay-ip-addr {
            type dhcp-ipv6-address;
            description
              "DHCPv6 server IPv6 address";
          }
          leaf server-vrf-name {
            type common-def:vrf-name;
            description
              "Name of the VRF that the DHCPv6 server is within";
          }
          container interface {
            description
              "Interface.";
            leaf interface-type {
              type dhcpv6-iftype;
              description
                "Interface type";
            }
            leaf interface-name {
              type dhcpv6-ifname;
              description
                "Interface name";
            }
          }
        }
      }
    }
  }

  augment "/common-def:routing-system/interface:interface/interface:ve/ipv6-config:ipv6" {
    uses interface-ve-dhcp;
  }
  augment "/interface:interface/interface:ethernet/interface:ipv6" {
    uses interface-phy-dhcp;
  }
}
