/*********************************************************************
 * Copyright (c) 2011 by Brocade Communications Systems, Inc.
 * All rights reserved.
 * brocade-acl-policy.yang: Brocade ACL Policy data model
 *
 * author: Saurabh Katiyar, sep 9, 2015.
 *
 *
 *********************************************************************/
module brocade-acl-policy {
  namespace "urn:brocade.com:mgmt:brocade-acl-policy";
  prefix aclpolicy;

  organization "Brocade Communications Systems, Inc.";
  contact
    "Brocade Communications Systems, Inc.      
     Postal: 130 Holger Way,              
     San Jose, CA 95134        
     U.S.A                   
     Tel: +1-408-333-8000
     E-mail: support@Brocade.com
     web: www.brocade.com.";
  description
    "This management module is an instrumentation to manage                 
     ACL Policy Configuration.";

  revision 2015-08-25 {
    description
      "Initial version of this management module.";
  }

  container acl-policy {
    uses global-acl-policy-cmds;
  }

  grouping global-acl-policy-cmds {
    container global-acl-policy-conf-cmds {
      leaf allow-conflicting-rules {
        type empty;
      }
      leaf allow-duplicate-rules {
        type empty;
      }
    }
  }
}
