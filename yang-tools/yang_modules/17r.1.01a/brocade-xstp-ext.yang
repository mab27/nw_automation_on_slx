/*********************************************************************
 * Copyright (c) 2011 by Brocade Communications Systems, Inc.
 * All rights reserved.
 * brocade-xstp-ext.yang: Brocade APPM module data model
 *
 * Feb 2011, 
 *
 *
 ********************************************************************/
module brocade-xstp-ext {
  namespace "urn:brocade.com:mgmt:brocade-xstp-ext";
  prefix xstp-extensions;

  import brocade-interface {
    prefix interface;
  }

  organization "Brocade Communications Systems, Inc.";
  contact
    "Brocade Communications Systems, Inc.
     Postal: 130 Holger Way
             San Jose, CA 95134
             U.S.A
     Tel: +1-408-333-8000
     E-mail: support@Brocade.com
     web: www.brocade.com.
    ";
  description
    "This module describes the data model for Spanning Tree
     Protocol
     
     Glossary of the terms used:
     ---------------------------
     CIST   Common and Internal Spanning Tree (IEEE 802.1Q)
    ";
  reference
    "IEEE Std 802.1Q: IEEE Standard for Local and metropolitan area
     networks - Virtual Bridged Local Area Networks, December 2005.
    ";

  revision 2011-02-22 {
    description
      "Initial Version";
  }

  typedef yes-no-type {
    type enumeration {
      enum "no" {
        value 1;
      }
      enum "yes" {
        value 2;
      }
    }
  }

  typedef on-off-type {
    type enumeration {
      enum "off" {
        value 1;
      }
      enum "on" {
        value 2;
      }
    }
  }

  typedef bridge-id-type {
    type string;
    description
      "The Bridge-Identifier, as used in the STP, to uniquely
       identify a bridge. First two octets (in network byte
       order) contain a priority value, and last 6 octets contain
       the MAC address used to refer to a bridge in a unique
       fashion (typically, the numerically smallest MAC address
       of all ports on the bridge)";
  }

  typedef stp-type {
    type enumeration {
      enum "none" {
        value 1;
      }
      enum "stp" {
        value 2;
        description
          "Classic Spanning Tree Protocol";
      }
      enum "rstp" {
        value 3;
        description
          "Rapid Spanning Tree Protocol";
      }
      enum "mstp" {
        value 4;
        description
          "Multiple Spanning Tree Protocol";
      }
      enum "pvstp" {
        value 5;
        description
          "Per-VLAN Spanning Tree Protocol";
      }
      enum "rpvstp" {
        value 6;
        description
          "Rapid Per-VLAN Spanning Tree Protocol";
      }
    }
    description
      "Indicate the variant of the spanning tree protocol";
  }

  typedef stp-port-state {
    type enumeration {
      enum "error" {
        value 1;
      }
      enum "disabled" {
        value 2;
        description
          "The port is inactive; does not participate in STP";
      }
      enum "blocking" {
        value 3;
        description
          "When a port is enabled, it first moves to a blocked
           state before listening to the network. The port
           does not participate in frame forwarding. BPDUs are
           still received and processed";
      }
      enum "listening" {
        value 4;
        description
          "In this state, the bridge still does not forward
           frames and does not learn network MAC addresses.
           The bridge does receive and process BPDUs and
           network management frames";
      }
      enum "learning" {
        value 5;
        description
          "The bridge port still discards incoming frames or
           frames switched over for forwarding. The bridge
           begins to incorporate MAC addresses associated with
           this port. BPDU and network management messages are
           still processed";
      }
      enum "forwarding" {
        value 6;
        description
          "This is the full functional state for a bridged
           port. In this state, the bridge does not discard
           incoming frames and forwards them to other ports;
           the bridge also forwards frames out the port. BPDUs
           and network management frames are still processed";
      }
      enum "discarding" {
        value 7;
        description
          "In MSTP and RSTP, disabled, blocking and listening
           states are combined together in one state known as
           discarding state";
      }
    }
  }

  typedef stp-port-role {
    type enumeration {
      enum "error" {
        value 1;
      }
      enum "designated" {
        value 2;
      }
      enum "root" {
        value 3;
      }
      enum "alternate" {
        value 4;
      }
      enum "backup" {
        value 5;
      }
      enum "disabled" {
        value 6;
      }
      enum "master" {
        value 7;
      }
    }
  }

  typedef stp-link-type {
    type enumeration {
      enum "point-to-point" {
        value 1;
        description
          "Point-to-point - enable rapid transition";
      }
      enum "shared" {
        value 2;
        description
          "Shared - disable rapid transition";
      }
    }
  }

  grouping bridge-attr {
    leaf priority {
      type uint32;
      description
        "Bridge priority (0..65535)";
    }
    leaf bridge-id {
      type bridge-id-type;
      description
        "Bridge id";
    }
    leaf hello-time {
      type uint32;
      description
        "The interval between two transmissions of BPDU packets
         sent by the Root Bridge to tell all other switches that
         it is indeed the Root Bridge (1..10 sec)";
    }
    leaf max-age {
      type uint32;
      description
        "The Max Age may be set to ensure that old information
         does not endlessly circulate through redundant paths in
         the network, preventing the effective propagation of
         new information (6..40 sec)";
    }
    leaf forward-delay {
      type uint32;
      description
        "Port on the Switch spends this time in the listening
         state while moving from the blocking state to the
         forwarding state (4..30 sec)";
    }
  }

  grouping transmit {
    leaf transmit-hold-count {
      type uint32;
      description
        "Maximum number of Hello packets transmitted per
         interval  (1..10)";
    }
    leaf migrate-time {
      type uint32;
      description
        "Bridge migrate time (sec)";
    }
  }

  grouping interface-list {
    uses ports-list;
  }

  grouping stp-brief-info {
    container root-bridge {
      uses bridge-attr;
    }
    container bridge {
      uses bridge-attr;
    }
  }

  grouping ports-list {
    list port {
      uses interface:interface-name-info;
      leaf spanningtree-enabled {
        type boolean;
        description
          "Is spanning tree enabled";
      }
      leaf if-index {
        type uint64;
        description
          "Interface index";
      }
      leaf interface-id {
        type uint64;
        description
          "Interface id";
      }
      leaf if-role {
        type stp-port-role;
        description
          "Interface role";
      }
      leaf if-state {
        type stp-port-state;
        description
          "Interface state";
      }
      leaf external-path-cost {
        type uint32;
        description
          "Designated external path cost";
      }
      leaf internal-path-cost {
        type uint32;
        description
          "Designated internal path cost";
      }
      leaf configured-path-cost {
        type uint32;
        description
          "Configured path cost";
      }
      leaf designated-port-id {
        type uint64;
        description
          "Designated port id";
      }
      leaf port-priority {
        type uint32;
        description
          "Port priority";
      }
      leaf designated-bridge-id {
        type bridge-id-type;
        description
          "Designated bridge Id";
      }
      leaf port-hello-time {
        type uint32;
        description
          "Port hello time";
      }
      leaf forward-transitions-count {
        type uint32;
        description
          "Number of forward transitions";
      }
      leaf received-stp-type {
        type stp-type;
        description
          "Received (rx) stp type";
      }
      leaf transmitted-stp-type {
        type stp-type;
        description
          "Transmitted (tx) stp type";
      }
      leaf edge-port {
        type on-off-type;
        description
          "Edge Port mode";
      }
      leaf auto-edge {
        type yes-no-type;
        description
          "Auto Edge";
      }
      leaf admin-edge {
        type yes-no-type;
        description
          "Admin Edge";
      }
      leaf edge-delay {
        type uint32;
        description
          "Edge delay";
      }
      leaf configured-root-guard {
        type on-off-type;
        description
          "Configured root guard";
      }
      leaf oper-root-guard {
        type on-off-type;
        description
          "Operational root guard";
      }
      leaf boundary-port {
        type yes-no-type;
        description
          "Is boundary";
      }
      leaf oper-bpdu-guard {
        type on-off-type;
        description
          "Operational BPDU guard";
      }
      leaf oper-bpdu-filter {
        type on-off-type;
        description
          "Pperational BPDU filter";
      }
      leaf link-type {
        type stp-link-type;
      }
      leaf rx-bpdu-count {
        type uint64;
        description
          "Received Bpdu count";
      }
      leaf tx-bpdu-count {
        type uint64;
        description
          "Transmitted Bpdu count";
      }
    }
  }

  grouping last-rcvd-record-info {
    description
      "Last received instance information. Client must fill these
       information in the RPC request if the previous call has
       returned partial information (has-more = true). When not
       filled, the RPC response would include spanning-tree
       instance information starting from the first instance.";
    container last-rcvd-instance {
      leaf instance-id {
        type uint32;
        description
          "Instance id of the last received spanning-tree
           instance.";
      }
    }
  }

  grouping records-info {
    description
      "Indicates the state of RPC response.";
    leaf has-more {
      type boolean;
      description
        "Indicates if this response is complete or not. Value 
         'true' indicates that the response is partial and there
         are more spanning-tree instances. Clients can retrieve
         next set of instances by passing the last received
         instance id (from ../last-instance/instance-id) in the
         subsequent RPC call.";
    }
    container last-instance {
      description
        "The 'last' spanning-tree instance included in this
         response.";
      leaf instance-id {
        type uint32;
        description
          "Instance id of the 'last' spanning-tree instance
           included in this response.";
      }
    }
  }

  rpc get-stp-brief-info {
    description
      "RPC to return spanning tree information similar to the
       CLI 'show spanning-tree'.";
    input {
      choice request-type {
        case getnext-request {
          description
            "Indicate the last received instance information
             for get-next type of requests.";
          uses last-rcvd-record-info;
        }
      }
    }
    output {
      container spanning-tree-info {
        leaf stp-mode {
          type stp-type;
          description
            "Type of the spanning tree protocol configured
             on this switch";
        }
        choice spanning-tree-mode {
          case stp {
            container stp {
              uses stp-brief-info;
              uses interface-list;
            }
          }
          case rstp {
            container rstp {
              uses stp-brief-info;
              uses transmit;
              uses interface-list;
            }
          }
          case mstp {
            container mstp {
              description
                "CIST information";
              uses stp-brief-info;
              uses transmit;
              uses interface-list;
            }
          }
          case pvstp {
            list pvstp {
              description
                "PVST instance information";
              key "vlan-id";
              leaf vlan-id {
                type interface:vlan-type;
              }
              uses stp-brief-info;
              uses transmit;
              uses interface-list;
            }
          }
          case rpvstp {
            list rpvstp {
              description
                "RPVST instance information";
              key "vlan-id";
              leaf vlan-id {
                type interface:vlan-type;
              }
              uses stp-brief-info;
              uses transmit;
              uses interface-list;
            }
          }
        }
      }
      uses records-info {
        description
          "Indicates if there are more instances; client
           can retrieve the by invoking the rpc again with
           the last record information.
           Applicable for PVST and RPVST modes only.";
      }
    }
  }
  rpc get-stp-mst-detail {
    description
      "RPC to return MSTP details.. 
       Equivalent to CLI 'show spanning-tree mst detail'.";
    input {
      choice request-type {
        case getnext-request {
          uses last-rcvd-record-info;
        }
      }
    }
    output {
      container cist {
        leaf cist-root-id {
          type bridge-id-type;
          description
            "CIST Root Id";
        }
        leaf cist-bridge-id {
          type bridge-id-type;
          description
            "CIST bridge Id";
        }
        leaf cist-reg-root-id {
          type bridge-id-type;
          description
            "CIST regional root Id";
        }
        leaf root-forward-delay {
          type uint32 {
            range "4..30";
          }
          description
            "CIST root forward delay (4..30 sec)";
        }
        leaf hello-time {
          type uint32 {
            range "1..10";
          }
          description
            "CIST root hello time (1..10 sec)";
        }
        leaf max-age {
          type uint32 {
            range "6..40";
          }
          description
            "CIST root maximum age (6..40 sec)";
        }
        leaf max-hops {
          type uint32 {
            range "1..40";
          }
          description
            "Hops the BPDU will be valid (1..40)";
        }
        leaf migrate-time {
          type uint32;
          description
            "Migration time (in seconds)";
        }
        container vlans {
          description
            "VLANs associated with this instance.";
          leaf-list vlan-id {
            type interface:vlan-type;
          }
        }
        uses ports-list;
      }
      list msti {
        key "instance-id";
        leaf instance-id {
          type uint32;
          description
            "MSTI Instance";
        }
        leaf msti-root-id {
          type bridge-id-type;
          description
            "MSTI Root Id";
        }
        leaf msti-bridge-id {
          type bridge-id-type;
          description
            "MSTI bridge Id";
        }
        leaf msti-bridge-priority {
          type uint32;
          description
            "MSTI Bridge priority";
        }
        container vlans {
          description
            "VLANs associated with this instance..";
          leaf-list vlan-id {
            type interface:vlan-type;
          }
        }
        uses ports-list;
      }
      uses records-info {
        description
          "";
      }
    }
  }
}
