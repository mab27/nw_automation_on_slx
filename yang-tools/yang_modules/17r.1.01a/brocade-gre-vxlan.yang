/*********************************************************************
 * Copyright (c) 2015 by Brocade Communications Systems, Inc.
 * All rights reserved.
 * brocade-gre-vxlan.yang: Brocade GRE Vxlan module data model
 *
 * April 2015, Youn-Mor Chen
 *
 *
 ********************************************************************/
module brocade-gre-vxlan {
  namespace "urn:brocade.com:mgmt:brocade-gre-vxlan";
  prefix gre-vxlan;

  import brocade-interface {
    prefix interface;
  }
  import ietf-inet-types {
    prefix inet;
  }
  import brocade-intf-loopback {
    prefix lo;
  }

  organization "Brocade Communications Systems, Inc.";
  contact
    "Brocade Communications Systems, Inc.
     Postal: 130 Holger Way
             San Jose, CA 95134
             U.S.A
     Tel: +1-408-333-8000
     E-mail: support@Brocade.com 
     web: www.brocade.com.";
  description
    "This module manages GRE Vxlan commands";

  revision 2015-07-14 {
    description
      "Initial version of this management module.";
  }

  grouping gre-vxlan-cmds {
    list tunnel {
      key "identifier";
      leaf identifier {
        type uint32 {
          range "1 .. 1024";
        }
      }
      container mode {
        container gre {
          leaf ip {
            type empty;
          }
        }
      }
      container gre-source {
        choice source-cmd {
          case ca-source-address {
            leaf source-address {
              type inet:ipv4-address;
            }
          }
          case ca-interface-loopback {
            leaf interface-loopback {
              type lo:intf-loopback-port-type;
            }
          }
          case ca-interface-ethernet {
            leaf interface-ethernet {
              type interface:interface-type;
            }
          }
          case ca-interface-ve {
            leaf interface-ve {
              type uint32 {
                range "1 .. 4095";
              }
            }
          }
        }
      }
      leaf tunnel-destination {
        type inet:ipv4-address;
      }
      leaf tunnel-shutdown {
        type empty;
      }
      container tunnel-router-interface {
        leaf router-ve {
          type uint32 {
            range "1 .. 4095";
          }
        }
      }
      leaf gre-ttl {
        type uint32 {
          range "1 .. 255";
        }
      }
      leaf gre-dscp {
        type uint32 {
          range "0 .. 63";
        }
      }
      leaf tunnel-name {
        type string {
          length "1..256";
        }
      }
      leaf dscp-ttl-mode {
        type enumeration {
          enum "uniform" {
            value 1;
          }
          enum "pipe" {
            value 2;
          }
        }
      }
      leaf statistics {
        type empty;
      }
      container keepalive {
        leaf time-interval {
          type uint32 {
            range "1 .. 32767";
          }
        }
        leaf retry-count {
          type uint32 {
            range "1 .. 255";
          }
        }
      }
    }
  }

  augment "/interface:interface" {
    uses gre-vxlan-cmds;
  }
}
