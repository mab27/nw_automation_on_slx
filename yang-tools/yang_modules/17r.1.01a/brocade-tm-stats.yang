/*********************************************************************
 * Copyright (c) 2016 by Brocade Communications Systems, Inc.
 * All rights reserved.
 * brocade-tm-stats.yang: Brocade TM  module data model
 *
 * Feb 2016, Harsh Patel
 *
 *
 ********************************************************************/
module brocade-tm-stats {
  namespace "urn:brocade.com:mgmt:brocade-tm-stats";
  prefix tm;

  import brocade-common-def {
    prefix common-def;
  }

  organization "Brocade Communications Systems, Inc.";
  contact
    "Brocade Communications Systems, Inc.
     Postal: 130 Holger Way
             San Jose, CA 95134
             U.S.A
     Tel: +1-408-333-8000
     E-mail: support@Brocade.com 
     web: www.brocade.com.";
  description
    "This module manages Traffic Manager stats";

  revision 2016-04-13 {
    description
      "Initial version of this management module.";
  }

  rpc clear-tm-voq-stat-ing-all-egr-all {
    input {
      leaf clear-tm-voq-ing-all-egress-port-all {
        default "true";
        type boolean;
      }
    }
  }
  rpc clear-tm-voq-stat-ing-all-egr-ifname {
    input {
      leaf clear-tm-voq-ing-all-egress-port-name {
        type string;
      }
    }
  }
  rpc clear-tm-voq-stat-slot-id-egr-all {
    input {
      leaf slot-id {
        mandatory true;
        type common-def:lc-number-type;
      }
      leaf clear-tm-voq-slot-egress-port-all {
        default "true";
        type boolean;
      }
    }
  }
  rpc clear-tm-voq-slot-id-egress-port-name {
    input {
      leaf slot-id {
        mandatory true;
        type common-def:lc-number-type;
      }
      leaf clear-tm-voq-slot-egress-port-name {
        mandatory true;
        type string;
      }
    }
  }
}
