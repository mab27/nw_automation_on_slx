/*********************************************************************
 * Copyright (c) 2011 by Brocade Communications Systems, Inc.
 * All rights reserved.
 * brocade-dot1x.yang: Brocade dot1x Data Model
 *
 * July 2011, Sai Srikanth, Brunda R R
 *
 *
 ********************************************************************/
module brocade-dot1x {
  namespace "urn:brocade.com:mgmt:brocade-dot1x";
  prefix dot1x;

  import brocade-interface {
    prefix interface;
  }

  organization "Brocade Communications Systems, Inc.";
  contact
    "Brocade Communications Systems, Inc.
     Postal: 130 Holger Way
             San Jose, CA 95134
             U.S.A
     Tel: +1-408-333-8000
     E-mail: support@Brocade.com 
     web: www.brocade.com.";
  description
    "This management module is an instrumentation to manage dot1x 
     feature. 
             
     IEEE 802.1X is an IEEE Standard for port-based Network Access 
     Control(PNAC). It is a networking protocol which provides an 
     authentication mechanism to devices wishing to attach to a
     LAN or WLAN.IEEE 802.1X defines the encapsulation of the 
     Extensible Authentication Protocol (EAP) over IEEE 802
     which is known as EAP over LAN or EAPoL.
     802.1x involves 3 parties
         Supplicant - Device which connects to network
         Authenticator - Network device such as ethernet switch
         Authentication server - A host running software that
                                 supports Radius and EAP Protocols
     This module defines the parameters used for the Port based 
     Network access control. Here authentication server is termed
     as dot1x server.
     
     Glossary of the terms used:
     ---------------------------
     EAPoL- Extensible Authentication Protocol over LAN
    ";
  reference
    "IEEE 802.1X, IEEE Standard for port-based Network Access 
     Control (PNAC), 2004.";

  revision 2011-07-13 {
    description
      "Initial version of the dot1x management module.";
  }

  typedef dot1x-supp-timeout-interval {
    type uint32 {
      range "1 .. 65535" {
        description
          "The definition for supplicant timeout of dot1x 
           server.";
      }
    }
    units "seconds";
  }

  typedef dot1x-tx-timeout-interval {
    type uint32 {
      range "1 .. 65535" {
        description
          "The definition for transmission period of dot1x.";
      }
    }
    units "seconds";
  }

  typedef dot1x-reauth-timeout-interval {
    type uint32 {
      range "1 .. 4294967295" {
        description
          "The definition for Reauthentication timeout 
           interval of dot1x.";
      }
    }
    units "seconds";
  }

  typedef dot1x-readinesstest-timeout-interval {
    type uint32 {
      range "1 .. 65535" {
        description
          "The definition for Readiness test timeout interval
           of dot1x server.";
      }
    }
  }

  container dot1x {
    description
      "This provides grouping of all the dot1x configuration
       elements.";
    leaf enable {
      type empty;
      description
        "This specifies if the port authentication is enabled 
         globally or not.
                         
         The presence of this leaf indicates that the port 
         authentication is enabled globally.";
    }
    container test {
      description
        "This provides the grouping of dot1x test elements.";
      leaf timeout {
        type dot1x-readinesstest-timeout-interval;
        default "10";
        description
          "This specifies the timeout period for dot1x 
           readiness test.";
      }
    }
  }

  grouping common-phy-dot1x-cmds {
    container dot1x {
      description
        "This provides grouping of all the dot1x configuration
         elements.";
      leaf authentication {
        type empty;
        description
          "This specifies if the dot1x is enabled on the port 
           or not.
                               
           The presence of this leaf indicates that the dot1x 
           is enabled on the port.";
      }
      leaf port-control {
        type enumeration {
          enum "auto" {
            value 1;
            description
              "Allow auto negotiation.";
          }
          enum "force-authorized" {
            value 2;
            description
              "Move port to authorized state forcefully.";
          }
          enum "force-unauthorized" {
            value 3;
            description
              "Move port to unauthorized state 
               forcefully.";
          }
        }
        description
          "This leaf specifies the port state.
           'auto' enables 802.1x authentication. The port 
           moves to authorized state only after successful 
           authentication. 'force-authorized' disables 802.1x
           and port moves to authorized state without any 
           authentication. 'force-unauthorized' causes the
           port to remain in the unauthorized state,
           ignoring all attempts by the client to 
           authenticate.";
      }
      leaf protocol-version {
        type uint32 {
          range "1 .. 2" {
            description
              "This Specifies the range for EAPoL 
               version.";
          }
        }
        default "2";
        description
          "This specifies the Extensible Authentication
           Protocol version.";
      }
      leaf quiet-period {
        type uint32 {
          range "1 .. 65535" {
            description
              "This specifies the supported range for 
               quiet period in HELD state.";
          }
        }
        default "60";
        description
          "This specifies the quiet period in HELD state.
           When the switch cannot authenticate the client
           it stays idle for this period of time and tries
           again. ";
      }
      leaf reauthMax {
        type uint32 {
          range "1 .. 10" {
            description
              "This specifies the maximum number of times 
               the reauthentication will be tried.";
          }
        }
        default "2";
        description
          "This specifies the number of reauthentication 
           attempts before becoming unauthorized.";
      }
      leaf max-req {
        type uint32 {
          range "1 .. 10" {
            description
              "This specifies the maximum number of times
               the ID Request Frame will be resent.";
          }
        }
        default "2";
        description
          "This specifies the number of times the EAP ID Request needs
           to be resent when response is not received.";
      }
      leaf reauthentication {
        type empty;
        description
          "This specifies if the re-authentication should be 
           done on a port.
                               
           The presence of this leaf indicates that the 
           re-authentication should be done.";
      }
      leaf filter-strict-security {
        type empty;
        description
          "This specifies if the strict mode should be done on a port.
           
           The presence of this leaf indicates that the strict mode
           should be done.";
      }
      container timeout {
        description
          "This provides the grouping of all the timeout
           configuration elements.";
        leaf re-authperiod {
          type dot1x-reauth-timeout-interval;
          default "3600";
          description
            "This specifies the number of seconds
             between re-authentication attempts.";
        }
        leaf supp-timeout {
          type dot1x-supp-timeout-interval;
          default "30";
          description
            "This specifies the supplicant response
             timeout. This is the amount of time the switch
             waits for a response before retransmitting 
             the request to the client when relaying a 
             request from the authentication server 
             to client.";
        }
        leaf tx-period {
          type dot1x-tx-timeout-interval;
          default "30";
          description
            "This specifies the number of seconds the 
             switch waits for response to an EAP 
             request/identity from client before
             retransmitting the request.";
        }
      }
    }
  }

  augment "/interface:interface/interface:ethernet" {
    uses common-phy-dot1x-cmds;
  }
}
