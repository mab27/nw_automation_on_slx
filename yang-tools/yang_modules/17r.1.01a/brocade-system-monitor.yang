/*********************************************************************
 * Copyright (c) 2011 by Brocade Communications Systems, Inc.
 * All rights reserved.
 * brocade-system-monitor.yang-: Brocade System Monitor Data Model
 *
 * May 2011,Priya Ahuja
 *
 *
 ********************************************************************/
module brocade-system-monitor {
  namespace "urn:brocade.com:mgmt:brocade-system-monitor";
  prefix system-monitor;

  import ietf-inet-types {
    prefix inet;
  }
  import brocade-system-capabilities {
    prefix c;
  }

  organization "Brocade Communications Systems, Inc.";
  contact
    "Address :  120 Holger Way
                San Jose, CA 95134
                U.S.A
     Phone    :  +1-408-333-8000
     E-mail   :  support@brocade.com
     Website  :  www.brocade.com";
  description
    "Data Model for Brocade's System Monitor configuration CLIs";

  revision 2011-11-16 {
    description
      "Addition of all FRUs";
  }
  revision 2011-04-29 {
    description
      "Initial modelling of Yang";
  }

  typedef supported-state {
    type bits {
      bit removed {
        position 0;
      }
      bit inserted {
        position 1;
      }
      bit on {
        position 2;
      }
      bit faulty {
        position 4;
      }
      bit none {
        position 5;
      }
      bit all {
        position 6;
      }
    }
  }

  typedef supported-actions {
    type bits {
      bit none {
        position 0;
      }
      bit all {
        position 1;
      }
      bit email {
        position 2;
      }
      bit raslog {
        position 3;
      }
    }
  }

  grouping system-monitor-group {
    container fan {
      container threshold {
        leaf marginal-threshold {
          type uint32;
        }
        leaf down-threshold {
          type uint32;
        }
      }
      container alert {
        leaf state {
          type supported-state;
        }
        leaf action {
          type supported-actions;
        }
      }
    }
    container power {
      container threshold {
        leaf marginal-threshold {
          type uint32;
        }
        leaf down-threshold {
          type uint32;
        }
      }
      container alert {
        leaf state {
          type supported-state;
        }
        leaf action {
          type supported-actions;
        }
      }
    }
    container temp {
      container threshold {
        leaf marginal-threshold {
          type uint32;
        }
        leaf down-threshold {
          type uint32;
        }
      }
    }
    container cid-card {
      container threshold {
        leaf marginal-threshold {
          type uint32;
        }
        leaf down-threshold {
          type uint32;
        }
      }
      container alert {
        leaf state {
          type supported-state;
        }
        leaf action {
          type supported-actions;
        }
      }
    }
    container compact-flash {
      container threshold {
        leaf marginal-threshold {
          type uint32;
        }
        leaf down-threshold {
          type uint32;
        }
      }
    }
    container MM {
      container threshold {
        leaf marginal-threshold {
          type uint32;
        }
        leaf down-threshold {
          type uint32;
        }
      }
    }
    container LineCard {
      container threshold {
        leaf marginal-threshold {
          type uint32;
        }
        leaf down-threshold {
          type uint32;
        }
      }
      container alert {
        leaf state {
          type supported-state;
        }
        leaf action {
          type supported-actions;
        }
      }
    }
    container SFM {
      container threshold {
        leaf marginal-threshold {
          type uint32;
        }
        leaf down-threshold {
          type uint32;
        }
      }
    }
  }

  container system-monitor {
    uses system-monitor-group;
    uses port-crc-monitoring-cmds;
    uses tm-cmds;
  }
  container system-monitor-mail {
    container fru {
      leaf enable {
        type empty;
      }
      list email-list {
        key "email";
        max-elements "5";
        leaf email {
          type string;
        }
      }
    }
    container sfp {
      leaf enable {
        type empty;
      }
      list email-list {
        key "email";
        max-elements "5";
        leaf email {
          type string;
        }
      }
    }
    container security {
      leaf enable {
        type empty;
      }
      list email-list {
        key "email";
        max-elements "5";
        leaf email {
          type string;
        }
      }
    }
    container interface {
      leaf enable {
        type empty;
      }
      list email-list {
        key "email";
        max-elements "5";
        leaf email {
          type string;
        }
      }
    }
    list relay {
      max-elements "1";
      key "host-ip";
      leaf host-ip {
        type inet:host;
      }
      leaf domain-name {
        type string {
          length "0 .. 64" {
            error-message
              "Domain name should be
               in the range 0-64";
          }
        }
        default "";
      }
    }
  }

  grouping port-crc-monitoring-cmds {
    container port {
      presence "true";
      container crc {
        leaf port-crc-mon-action {
          type enumeration {
            enum "raslog" {
              value 1;
            }
            enum "port-shutdown" {
              value 2;
            }
          }
        }
        leaf port-crc-mon-interval {
          type uint16 {
            range "2 .. 65535";
          }
        }
        leaf port-crc-mon-threshold {
          type uint8 {
            range "1 .. 10";
          }
        }
        leaf port-crc-mon-disable {
          type empty;
        }
      }
    }
  }

  grouping tm-cmds {
    container tm {
      when "((/c:capabilities/c:tm = \"true\"))";
      presence "true";
      container discard-packet {
        leaf tm-discard-packet-action {
          type enumeration {
            enum "raslog" {
              value 1;
            }
          }
        }
        leaf tm-discard-packet-threshold {
          type uint32 {
            range "0 .. 10000";
          }
        }
        leaf tm-discard-packet-interval {
          type uint16 {
            range "10 .. 2880";
          }
        }
      }
      container discard-voq-packet {
        leaf tm-discard-voq-packet-action {
          type enumeration {
            enum "raslog" {
              value 1;
            }
          }
        }
        leaf tm-discard-voq-packet-threshold {
          type uint32 {
            range "0 .. 10000";
          }
        }
        leaf tm-discard-voq-packet-interval {
          type uint16 {
            range "10 .. 2880";
          }
        }
      }
      container delete-packet {
        leaf tm-delete-packet-action {
          type enumeration {
            enum "raslog" {
              value 1;
            }
          }
        }
        leaf tm-delete-packet-threshold {
          type uint32 {
            range "0 .. 10000";
          }
        }
        leaf tm-delete-packet-interval {
          type uint16 {
            range "10 .. 2880";
          }
        }
      }
    }
  }
}
