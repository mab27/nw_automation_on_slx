/*******************************************************************
 * Copyright (c) 2014 by Brocade Communications Systems, Inc.
 * All rights reserved.
 * brocade-vrf.yang: Brocade VRF module data model
 *
 *
 ******************************************************************/
module brocade-ipv6-rtm {
  namespace "urn:brocade.com:mgmt:brocade-ipv6-rtm";
  prefix ipv6-route;

  import ietf-inet-types {
    prefix inet;
  }
  import brocade-common-def {
    prefix common-def;
  }
  import brocade-vrf {
    prefix vrf;
  }

  organization "Brocade Communications Systems, Inc.";
  contact
    "Brocade Communications Systems, Inc.
     Postal: 130 Holger Way
             San Jose, CA 95134
              U.S.A
     Tel: +1-408-333-8000
     E-mail: support@Brocade.com 
     web: www.brocade.com.";
  description
    "This management module is for IP Routes.";

  revision 2013-10-22 {
    description
      "Initial version of this management module.";
  }

  grouping dynamic-leak-config {
    container import {
      list routes {
        description
          "import IPV6 routes";
        key "src-vrf route-map";
        leaf src-vrf {
          type common-def:vrf-name;
        }
        leaf route-map {
          type common-def:name-string63;
        }
      }
    }
  }

  grouping ipv6-route-attrib {
    container route-attributes {
      leaf metric {
        type uint32 {
          range "1..16" {
            error-message "% Error: Value out of range at '^' marker";
          }
        }
      }
      leaf distance {
        type uint32 {
          range "1..254" {
            error-message "% Error: Value out of range at '^' marker";
          }
        }
      }
      leaf tag {
        type uint32;
        description
          "Tag can be configured to filter the static routes
           for route redistribution.
           Default value is 0, indicating no tag.";
      }
    }
  }

  grouping ipv6-rtm-route-config {
    container route {
      list static-route-nh {
        key "static-route-dest static-route-next-hop";
        leaf static-route-dest {
          type inet:ipv6-prefix;
        }
        leaf static-route-next-hop {
          type inet:ipv6-address;
        }
        uses ipv6-route-attrib;
      }
      list static-route-oif {
        key "static-route-dest static-route-oif-type static-route-oif-name";
        leaf static-route-dest {
          type inet:ipv6-prefix;
        }
        leaf static-route-oif-type {
          type enumeration {
            enum "ethernet" {
              value 1;
            }
            enum "ve" {
              value 4;
            }
            enum "null" {
              value 5;
            }
          }
        }
        leaf static-route-oif-name {
          type string {
            length "1..16";
          }
        }
        uses ipv6-route-attrib;
      }
      list link-local-static-route-nh {
        key "link-local-static-route-dest link-local-nexthop link-local-route-oif-type link-local-route-oif-name";
        leaf link-local-static-route-dest {
          type inet:ipv6-prefix;
        }
        leaf link-local-nexthop {
          type inet:ipv6-address;
        }
        leaf link-local-route-oif-type {
          type enumeration {
            enum "ethernet" {
              value 1;
            }
            enum "management" {
              value 3;
            }
            enum "ve" {
              value 4;
            }
            enum "null" {
              value 5;
            }
          }
        }
        leaf link-local-route-oif-name {
          type string {
            length "1..16";
          }
        }
        uses ipv6-route-attrib;
      }
      list static-route-nh-vrf {
        key "static-route-next-vrf-dest next-hop-vrf static-route-next-hop";
        leaf static-route-next-vrf-dest {
          type inet:ipv6-prefix;
        }
        leaf next-hop-vrf {
          type common-def:vrf-name;
        }
        leaf static-route-next-hop {
          type inet:ipv6-address;
        }
      }
      list link-local-static-route-nh-vrf {
        key "static-route-next-vrf-dest next-hop-vrf link-local-next-hop link-local-route-oif-type  link-local-route-oif-name";
        leaf static-route-next-vrf-dest {
          type inet:ipv6-prefix;
        }
        leaf next-hop-vrf {
          type common-def:vrf-name;
        }
        leaf link-local-next-hop {
          type inet:ipv6-address;
        }
        leaf link-local-route-oif-type {
          type enumeration {
            enum "ethernet" {
              value 1;
            }
            enum "management" {
              value 3;
            }
            enum "ve" {
              value 4;
            }
            enum "null" {
              value 5;
            }
          }
        }
        leaf link-local-route-oif-name {
          type string {
            length "1..16";
          }
        }
      }
      list ipv6-static-route-oif-vrf {
        key "static-route-next-vrf-dest next-hop-vrf static-route-oif-type static-route-oif-name";
        leaf static-route-next-vrf-dest {
          type inet:ipv6-prefix;
        }
        leaf next-hop-vrf {
          type common-def:vrf-name;
        }
        leaf static-route-oif-type {
          type enumeration {
            enum "ethernet" {
              value 1;
            }
            enum "ve" {
              value 4;
            }
            enum "null" {
              value 5;
            }
          }
        }
        leaf static-route-oif-name {
          type string {
            length "1..16";
          }
        }
      }
    }
  }

  augment "/common-def:ipv6" {
    uses ipv6-rtm-route-config;
    uses dynamic-leak-config;
  }
  augment "/vrf:vrf/vrf:address-family/vrf:ipv6/vrf:unicast" {
    container ipv6 {
      uses ipv6-rtm-route-config;
      uses dynamic-leak-config;
    }
  }
}
