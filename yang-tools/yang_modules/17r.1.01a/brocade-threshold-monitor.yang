/*********************************************************************
* Copyright (c) 2011 by Brocade Communications Systems, Inc.
* All rights reserved.
* brocade-threshold-monitor.yang-: Brocade System Monitor Data Model
*
* November 2011,Ramya Rangarajan
*
*
********************************************************************/
module brocade-threshold-monitor {
  namespace "urn:brocade.com:mgmt:brocade-threshold-monitor";
  prefix threshold-monitor;

  organization "Brocade Communications Systems, Inc.";
  contact
    "Address :  120 Holger Way
         San Jose, CA 95134
         U.S.A
     Phone    :  +1-408-333-8000
     E-mail   :  support@brocade.com
     Website  :  www.brocade.com";
  description
    "Data Model for Brocade's System Monitor configuration CLIs";

  revision 2011-11-24 {
    description
      "Initial modelling of Yang";
  }

  typedef supported-actions {
    type bits {
      bit none {
        position 0;
      }
      bit all {
        position 1;
      }
      bit email {
        position 2;
      }
      bit raslog {
        position 3;
      }
      bit loginfo {
        position 4;
      }
    }
  }

  typedef supported-config {
    type string;
  }

  grouping threshold-monitor-group {
    container threshold-monitor {
      container sfp {
        leaf apply {
          type supported-config;
        }
        leaf pause {
          type empty;
        }
        list policy {
          key "policy_name";
          leaf policy_name {
            type string;
          }
          list area {
            key "type area_value";
            leaf type {
              type enumeration {
                enum "1GSR" {
                  value 0;
                }
                enum "1GLR" {
                  value 1;
                }
                enum "1GCOP" {
                  value 2;
                }
                enum "10GUSR" {
                  value 3;
                }
                enum "10GSR" {
                  value 4;
                }
                enum "10GLR" {
                  value 5;
                }
                enum "10GER" {
                  value 6;
                }
                enum "40GSR" {
                  value 7;
                }
                enum "40GSRINT" {
                  value 8;
                }
                enum "40GESR" {
                  value 9;
                }
                enum "40GLR" {
                  value 10;
                }
                enum "100GSR" {
                  value 11;
                }
                enum "100GLR" {
                  value 12;
                }
                enum "100GPSM" {
                  value 13;
                }
                enum "100GCWDM" {
                  value 14;
                }
                enum "100GCLR" {
                  value 15;
                }
                enum "100GLRLT" {
                  value 16;
                }
                enum "10GZR" {
                  value 17;
                }
                enum "1GCWDM" {
                  value 18;
                }
                enum "10GDWDMT" {
                  value 19;
                }
                enum "40GER" {
                  value 20;
                }
                enum "40GLM" {
                  value 21;
                }
                enum "100GESR" {
                  value 22;
                }
                enum "100GAOC" {
                  value 23;
                }
              }
            }
            leaf area_value {
              type enumeration {
                enum "Temperature" {
                  value 0;
                }
                enum "RXP" {
                  value 1;
                }
                enum "TXP" {
                  value 2;
                }
                enum "Current" {
                  value 3;
                }
                enum "Voltage" {
                  value 4;
                }
              }
            }
            container threshold {
              leaf high-threshold {
                type int32;
              }
              leaf low-threshold {
                type int32;
              }
              leaf buffer {
                type int32;
              }
            }
            container alert {
              container above {
                leaf above-highthresh-action {
                  type supported-actions;
                }
              }
              container below {
                leaf below-highthresh-action {
                  type supported-actions;
                }
                leaf below-lowthresh-action {
                  type supported-actions;
                }
              }
            }
          }
        }
      }
      container Cpu {
        leaf poll {
          type uint32 {
            range "10 .. 3600" {
              error-message
                "Polling interval must be in range
                 10 - 3600";
            }
          }
          default "120";
        }
        leaf retry {
          type uint32 {
            range "1 .. 100" {
              error-message "Retries must be in range 1 - 100";
            }
          }
          default "3";
        }
        leaf limit {
          type uint32 {
            range "0 .. 80" {
              error-message "Usage limit must be in range 0 - 80";
            }
          }
          default "75";
        }
        leaf actions {
          type enumeration {
            enum "none" {
              value 1;
            }
            enum "raslog" {
              value 2;
            }
            enum "loginfo" {
              value 129;
            }
          }
          default "none";
        }
      }
      container Memory {
        leaf poll {
          type uint32 {
            range "10 .. 3600" {
              error-message
                "Polling interval must be in range
                 10 - 3600";
            }
          }
          default "120";
        }
        leaf retry {
          type uint32 {
            range "1 .. 100" {
              error-message "Retries must be in range 1 - 100";
            }
          }
          default "3";
        }
        leaf limit {
          type uint32 {
            range "0 .. 80" {
              error-message "Memory usage limit must be in range 0 - 80";
            }
          }
          default "60";
        }
        leaf high-limit {
          type uint32 {
            range "0 .. 80" {
              error-message "Memory usage high-limit must be in range 0 - 80";
            }
          }
          default "70";
        }
        leaf low-limit {
          type uint32 {
            range "0 .. 80" {
              error-message "Memory usage low-limit must be in range 0 - 80";
            }
          }
          default "40";
        }
        leaf actions {
          type enumeration {
            enum "none" {
              value 1;
            }
            enum "raslog" {
              value 2;
            }
            enum "loginfo" {
              value 129;
            }
          }
          default "none";
        }
      }
      container Buffer {
        leaf poll {
          type uint32 {
            range "10 .. 3600" {
              error-message
                "Polling interval must be in range
                 10 - 3600";
            }
          }
          default "120";
        }
        leaf retry {
          type uint32 {
            range "1 .. 100" {
              error-message "Retries must be in range 1 - 100";
            }
          }
          default "3";
        }
        leaf limit {
          type uint32 {
            range "0 .. 80" {
              error-message "Usage limit must be in range 0 - 80";
            }
          }
          default "75";
        }
        leaf actions {
          type enumeration {
            enum "none" {
              value 1;
            }
            enum "raslog" {
              value 2;
            }
            enum "loginfo" {
              value 129;
            }
          }
          default "none";
        }
      }
    }
  }

  container threshold-monitor-hidden {
    uses threshold-monitor-group;
  }
}
