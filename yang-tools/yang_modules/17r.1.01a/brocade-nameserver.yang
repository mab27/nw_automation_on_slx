/*********************************************************************
 * Copyright (c) 2011-2012 by Brocade Communications Systems, Inc.
 * All rights reserved.
 * brocade-nameserver.yang: Brocade Name Server Data Model
 *
 * July 2011, Murali Lachireddy, Dave Bhuyan, Sanjeev C Joshi
 *
 *
 ********************************************************************/
module brocade-nameserver {
  namespace "urn:brocade.com:mgmt:brocade-nameserver";
  prefix name-server;

  import tailf-common {
    prefix tailf;
  }
  import brocade-common-def {
    prefix common-def;
  }

  organization "Brocade Communications Systems, Inc.";
  contact
    "Brocade Communications Systems, Inc.
     Postal: 130 Holger Way
             San Jose, CA 95134
              U.S.A
     Tel: +1-408-333-8000
     E-mail: support@Brocade.com
     web: www.brocade.com.";
  description
    "The management module is an instrumentation to manage the
     Fibre Channel (FC) Name Server, which realizes the FC-GS-6
     requirements.
     
     This module provides the means for monitoring the operation
     of, and configuring some parameters of, one or more instances
     of Fibre Channel Name Server functionality.
     
     The Fibre Channel Name Server provides a way for N_Ports and
     NL_Ports to register and discover Fibre Channel attributes.
     Such attributes include names, addresses, types, features,
     etc., at various protocol layers, including upper layer
     protocols specific to Fibre Channel (which are sometimes
     called 'FC-4s').
     
     Physically, Fibre Channel is an interconnection of multiple
     communication points, called N_Ports, interconnected either by
     a switching network, called a Fabric, or by a point-to-point
     link. A Fibre Channel 'node' consists of one or more N_Ports.
     A Fabric may consist of multiple Interconnect Elements, some
     of which are switches.  An N_Port connects to the Fabric via a
     port on a switch called an F_Port.  When multiple FC nodes are
     connected to a single port on a switch via an 'Arbitrated Loop'
     topology, the switch port is called an FL_Port, and the nodes'
     ports are called NL_Ports.  The term Nx_Port is used to refer
     to either an N_Port or an NL_Port.
     
     Glossary of the terms used:
     ---------------------------
     F_Port              -   Port that connects to a node point-to-point.
     
     FL_Port             -   Port that connects to a FC-AL loop.
     
     Frame Redirection   -   A Brocade-proprietary feature that uses
                            zoning to define a redirected path for
                            Initiator and Target traffic. Traffic is
                            redirected to a network appliance via a
                            virtual initiator and virtual target.
     
     iSCSI               -   Internet Small Computer System
                            Interface.
     
     N_Port              -   Port on a node used with both FC-P2P
                            or FC-SW topologies.
     
     NL_Port             -   Port on a node used with an FC-AL
                            topology.
     
     NPIV                -   N_Port ID Virtualization.
     
     Nx_Port             -   A generic port that can become an N_port
                            or NL_Port.
     
     Port ID (PID)       -   The Fibre Channel address ID in DDAAPP
                            hexadecimal format.
     
     SCR                 -   State Change Registration.
     
     Shared Area         -   A Brocade-proprietary method of
                            addressing where the area address uses
                            the traditional 8-bits of the FCID
                            'AREA' field, plus an additional 2-bits
                            from the FCID 'AL_PA' field.
     
     Translate Domain    -   FOS FC routing (FCR) creates an
                            translate domain in the local edge
                            fabric and this represents the
                            remote edge fabric
                            (also, 'Xlate Domain')
     
     Access Gateway (AG) -   The Access Gateway feature, a software 
                            feature that allows a Brocade switch 
                            to act as transparent 'port expander', 
                            connecting multiple FC devices
                            (typically host HBA ports) to a single 
                            FC fabric port (F_Port). The Access 
                            Gateway connects to the fabric using 
                            the FC N_Port protocol rather than the 
                            E_Port protocol normally used by a 
                            switch, and uses the FC-FS N_Port ID 
                            Virtualization (NPIV) facility to 
                            allow its client devices to connect to 
                            the FC fabric. Although it uses its 
                            switching logic to allow the attached 
                            devices to send and receive FC traffic 
                            to the fabric, it is not recognized by 
                            the fabric as a 'switch' and therefore
                            doesn't consume a domain ID and doesn't
                            participate in the switch-to-switch 
                            traffic normal to an FC fabric.
    ";
  reference
    "ANSI INCITS 332-1999, Fibre Channel - Arbitrated Loop - 2
     (FC-AL-2).
     
     ANSI INCITS 433-2006, Fibre Channel - Link Services
     (FC-LS).
     
     ANSI INCITS 463-2010, Fibre Channel - Generic Services - 6
     (FC-GS-6).";

  revision 2012-03-07 {
    description
      "Name Server management module.";
  }

  typedef nameserver-fcid-hexstring-type {
    type string {
      length "8";
      pattern "[0][x][0-9a-fA-F]*";
    }
    description
      "The definition to specify the Fibre Channel Address ID.
       It is a 24-bit value unique within the address space of a
       Fabric. This definition is canonical representation of the
       address in hexadecimal format.";
  }

  typedef nameserver-portid-type {
    type string {
      length "6";
      pattern "[0-9a-fA-F]*";
    }
    description
      "Definition of the Fibre Channel address for an Nx_Port
       (FCID). Uses hexadecimal format.";
  }

  typedef nameserver-devicetype-type {
    type string {
      length "0..64";
      pattern "Undefined|Unknown(initiator/target)|                     Physical Initiator|NPIV Initiator|                     Virtual Initiator|iSCSI Initiator|Physical Target|                     NPIV Target|Virtual Target|iSCSI Target|                     Physical Initiator+Target|NPIV Initiator+Target|                     Virtual Initiator+Target|iSCSI Initiator+Target";
    }
    description
      "The definition for the type and role of a device,
       where the device type is either a Physical, Virtual, NPIV,
       or iSCSI. And, the role is either Initiator, Target, or
       Initiator+Target. If the device role is not registered, the
       display indicates this as 'unknown. If the device registers
       a type that is not Physical, Virtual, NPIV, or iSCSI, the
       type is listed as 'undefined'.";
  }

  typedef nameserver-fc4s-type {
    type string {
      length "0..16";
      pattern "none|FCP|IPFC";
    }
    description
      "The definition to specify the Fibre Channel FC4 type
       registered by the device as a string. If the type is not
       'FCP' or 'IPFC', and is not 'none', then this is left
       blank.";
  }

  typedef nameserver-symbolic-name-type {
    type string {
      length "0..256";
    }
    description
      "Definition of the user defined name (ASCII string).";
  }

  typedef nameserver-porttype-type {
    type string {
      length "0..8";
      pattern "U|N|NL|NX|F|FL|[0][x][0-9a-fA-F]*";
    }
    description
      "Definition of the Fibre Channel port type:
       
       U       -   Unknown (the port has not supplied port type)
       N       -   N_Port
       NL      -   NL_Port
       NX      -   Nx_Port
       F       -   F_Port
       FL      -   FL_Port
       0xnn    -   Other: A two-digit numeric value of the
                  undefined/unrecognized type supplied by
                  the port.
      ";
  }

  typedef nameserver-cos-type {
    type string {
      length "0..8";
      pattern "F|1|2|3|,";
    }
    description
      "Definition of the Fibre Channel class of service
       (comma separated list).
       
       F       -   Class F
       1       -   Class 1
       2       -   Class 2
       3       -   Class 3
      ";
  }

  typedef nameserver-sharearea-type {
    type string {
      length "0..3";
      pattern "Yes|No";
    }
    description
      "Definition for the Brocade shared area addressing method.
       If 'yes' then the port uses shared area addressing.";
  }

  typedef nameserver-redirect-type {
    type string {
      length "0..3";
      pattern "Yes|No";
    }
    description
      "Definition for Brocade Frame Redirection. If 'Yes' then
       the port is involved in Frame Redirection zoning.";
  }

  typedef nameserver-xlatedomain-type {
    type string {
      length "0..3";
      pattern "Yes|No";
    }
    description
      "Definition for the translate domain property. If 'Yes'
       then the device enters the fabric via a translate domain.";
  }

  typedef nameserver-connected-via-ag-type {
    type string {
      length "0..3";
      pattern "Yes|No";
    }
    description
      "Definition for the Connected Via AG. If 'Yes' then the 
       device enters the fabric via Access Gateway.";
  }

  typedef nameserver-ag-base-device-type {
    type string {
      length "0..3";
      pattern "Yes|No";
    }
    description
      "Definition for the base AG Device. If 'Yes' then the 
       device is the Base Access Gateway Device.";
  }

  typedef nameserver-real-type {
    type string {
      length "0..3";
      pattern "Yes|No";
    }
    description
      "Definition for the Real Device. If 'Yes' then the device
       entered in the fabric via AG is a Physical Device, if 'No' 
       then the device is a Virtual Device.";
  }

  typedef nameserver-cascaded-type {
    type string {
      length "0..3";
      pattern "Yes|No";
    }
    description
      "Definition for the Connected Via Cascaded AG. If 'Yes'
       then the device enters the fabric via a Cascaded AG.";
  }

  augment "/common-def:show" {
    container name-server {
      description
        "Sub-actions of this command will display information
         about Fibre Channel devices stored within the Name
         Server directory.";
      tailf:action "brief" {
        description
          "This function is to get a list of devices, listed
           by FCID, that are stored in the Name Server
           database.";
        input;
      }
      tailf:action "detail" {
        description
          "A function to display the detailed information of
           the devices stored in the Name Server database.";
        output {
          list show-nameserver {
            key "nameserver-portid";
            description
              "The list of all Nx_Ports registered in the
               Name Server database of this managed
               device. Each row represents a FC device
               (Nx_Port) logged in and registered with the
               Name Server.";
            leaf nameserver-portid {
              type nameserver-portid-type;
              description
                "The Fibre Channel Address Identifier
                 of this Nx_Port.";
            }
            leaf nameserver-portname {
              type common-def:wwn-type;
              description
                "The Port_Name (WWN) of this Nx_Port.";
            }
            leaf nameserver-nodename {
              type common-def:wwn-type;
              description
                "The Node_Name (WWN) of this Nx_Port.";
            }
            leaf nameserver-scr {
              type uint32;
              description
                "Indicates the state change
                 notifications that the device has
                 registered for.";
            }
            leaf nameserver-fc4s {
              type nameserver-fc4s-type;
              description
                "Indicates the Fibre Channel FC4
                 services supported by the device.";
            }
            leaf nameserver-portsymb {
              type nameserver-symbolic-name-type;
              description
                "The user-defined name of this port.";
            }
            leaf nameserver-nodesymb {
              type nameserver-symbolic-name-type;
              description
                "The user-defined name of the node of
                 this port.";
            }
            leaf nameserver-fabric-portname {
              type common-def:wwn-type;
              description
                "Indicates the fabric port name (WWN)
                 of this port.";
            }
            leaf nameserver-permanent-portname {
              type common-def:wwn-type;
              description
                "Indicates the permanent port name (WWN)
                 of this port.";
            }
            leaf nameserver-devicetype {
              type nameserver-devicetype-type;
              description
                "Indicates the type and role of the
                 device.";
            }
            leaf nameserver-index {
              type uint32;
              description
                "Indicates the port index number.";
            }
            leaf nameserver-porttype {
              type nameserver-porttype-type;
              description
                "Indicates the Fibre Channel port
                 type.";
            }
            leaf nameserver-cos {
              type nameserver-cos-type;
              description
                "Indicates the Fibre Channel Class of
                 Service supported by the device.";
            }
            leaf nameserver-sharearea {
              type nameserver-sharearea-type;
              description
                "Indicates whether or not the port
                 utilizes the Brocade Shared Area method
                 of Fibre Channel addressing.";
            }
            leaf nameserver-redirect {
              type nameserver-redirect-type;
              description
                "Indicates whether or not the device
                 is involved in Brocade Frame
                 Redirection zoning.";
            }
            leaf nameserver-xlatedomain {
              type nameserver-xlatedomain-type;
              description
                "Indicates whether or not the device
                 enters the fabric via a translate
                 domain.";
            }
            leaf nameserver-connected-via-ag {
              type nameserver-connected-via-ag-type;
              description
                "Indicates whether or not the device
                 enters the fabric via Access Gateway.";
            }
            leaf nameserver-ag-base-device {
              type nameserver-ag-base-device-type;
              description
                "Indicates whether or not the device  
                 is a Base Access Gateway Device.";
            }
            leaf nameserver-real {
              type nameserver-real-type;
              description
                "Indicates whether or not the device
                 entered in the fabric via AG is a 
                 Physical Device.";
            }
            leaf nameserver-cascaded {
              type nameserver-cascaded-type;
              description
                "Indicates whether or not the device
                 enters the fabric via a Cascaded AG.";
            }
          }
        }
      }
      tailf:action "nodefind" {
        description
          "A function to get all nodes matching the
           specified information.";
        input {
          choice pid-or-wwn {
            case wwn {
              leaf wwn {
                type common-def:wwn-type;
                mandatory true;
                description
                  "This specifies the worldwide name
                   of the device to search for.";
              }
            }
            case pid {
              leaf pid {
                type nameserver-fcid-hexstring-type;
                mandatory true;
                description
                  "This specifies the FCID (PID) of
                   device to search for.";
              }
            }
          }
        }
      }
      tailf:action "zonemember" {
        description
          "A function to get all nodes zoned with the
           device matching the specified information.";
        input {
          choice pid-or-wwn {
            case wwn {
              leaf wwn {
                type common-def:wwn-type;
                mandatory true;
                description
                  "This specifies the worldwide name
                   of the device to search for.";
              }
            }
            case pid {
              leaf pid {
                type nameserver-fcid-hexstring-type;
                mandatory true;
                description
                  "This specifies the FCID (PID) of
                   device to search for.";
              }
            }
          }
        }
      }
    }
  }
  rpc get-nameserver-detail {
    description
      "A function to display the detailed information of
       the devices stored in the Name Server database.";
    output {
      list show-nameserver {
        key "nameserver-portid";
        description
          "The list of all Nx_Ports registered in the
           Name Server database of this managed
           device. Each row represents a FC device
           (Nx_Port) logged in and registered with the
           Name Server.";
        leaf nameserver-portid {
          type nameserver-portid-type;
          description
            "The Fibre Channel Address Identifier
             of this Nx_Port.";
        }
        leaf nameserver-portname {
          type common-def:wwn-type;
          description
            "The Port_Name (WWN) of this Nx_Port.";
        }
        leaf nameserver-nodename {
          type common-def:wwn-type;
          description
            "The Node_Name (WWN) of this Nx_Port.";
        }
        leaf nameserver-scr {
          type uint32;
          description
            "Indicates the state change
             notifications that the device has
             registered for.";
        }
        leaf nameserver-fc4s {
          type nameserver-fc4s-type;
          description
            "Indicates the Fibre Channel FC4
             services supported by the device.";
        }
        leaf nameserver-portsymb {
          type nameserver-symbolic-name-type;
          description
            "The user-defined name of this port.";
        }
        leaf nameserver-nodesymb {
          type nameserver-symbolic-name-type;
          description
            "The user-defined name of the node of
             this port.";
        }
        leaf nameserver-fabric-portname {
          type common-def:wwn-type;
          description
            "Indicates the fabric port name (WWN)
             of this port.";
        }
        leaf nameserver-permanent-portname {
          type common-def:wwn-type;
          description
            "Indicates the permanent port name (WWN)
             of this port.";
        }
        leaf nameserver-devicetype {
          type nameserver-devicetype-type;
          description
            "Indicates the type and role of the
             device.";
        }
        leaf nameserver-index {
          type uint32;
          description
            "Indicates the port index number.";
        }
        leaf nameserver-porttype {
          type nameserver-porttype-type;
          description
            "Indicates the Fibre Channel port
             type.";
        }
        leaf nameserver-cos {
          type nameserver-cos-type;
          description
            "Indicates the Fibre Channel Class of
             Service supported by the device.";
        }
        leaf nameserver-sharearea {
          type nameserver-sharearea-type;
          description
            "Indicates whether or not the port
             utilizes the Brocade Shared Area method
             of Fibre Channel addressing.";
        }
        leaf nameserver-redirect {
          type nameserver-redirect-type;
          description
            "Indicates whether or not the device
             is involved in Brocade Frame
             Redirection zoning.";
        }
        leaf nameserver-xlatedomain {
          type nameserver-xlatedomain-type;
          description
            "Indicates whether or not the device
             enters the fabric via a translate
             domain.";
        }
        leaf nameserver-connected-via-ag {
          type nameserver-connected-via-ag-type;
          description
            "Indicates whether or not the device
             enters the fabric via Access Gateway.";
        }
        leaf nameserver-ag-base-device {
          type nameserver-ag-base-device-type;
          description
            "Indicates whether or not the device  
             is a Base Access Gateway Device.";
        }
        leaf nameserver-real {
          type nameserver-real-type;
          description
            "Indicates whether or not the device
             entered in the fabric via AG is a 
             Physical Device.";
        }
        leaf nameserver-cascaded {
          type nameserver-cascaded-type;
          description
            "Indicates whether or not the device
             enters the fabric via a Cascaded AG.";
        }
      }
    }
  }
}
