/*********************************************************************
 * Copyright (c) 2014 by Brocade Communications Systems, Inc.
 * All rights reserved.
 * brocade-openflow.yang: Brocade Openflow Management Data Model
 *
 *
 *
 ********************************************************************/
module brocade-openflow {
  namespace "urn:brocade.com:mgmt:brocade-openflow";
  prefix openflow;

  import ietf-inet-types {
    prefix inet;
  }
  import brocade-common-def {
    prefix common-def;
  }
  import brocade-interface {
    prefix interface;
  }
  import brocade-system-capabilities {
    prefix c;
  }

  organization "Brocade Communications Systems, Inc.";
  contact
    "Brocade Communications Systems, Inc.
     Postal:\t130 Holger Way
     San Jose, CA 95134 U.S.A
     Tel: +1-408-333-8000
     E-mail: support@Brocade.com 
     web: www.brocade.com.";
  description
    "
     This module defines configuration commands related for enableing openflow  
     
     Configuration examples:
     openflow enable ver13
     openflow enable ver10
     openflow controller passive
    ";

  revision 2014-08-12 {
    description
      "First implementation of Openflow Interface configuration commands";
  }

  typedef name32-type {
    description
      "Defines common type for names. Name can contain maximum of
       32 characters. Alphabets, digits, hyphen and underscore
       charcters are allowed.";
    type string {
      pattern "[-_a-zA-Z0-9]{1,32}";
    }
  }

  typedef ui32-vlan-range {
    type string {
      pattern "(([1-9][0-9]{0,2})|([1-3][0-9]{3})|(40[0-8][0-9])|(4090))(-((1[0-9]{1,2})|([2-9][0-9]{0,2})|([1-3][0-9]{3})|(40[0-8][0-9])|(4090)))?((,((1[0-9]{1,2})|([2-9][0-9]{0,2})|([1-3][0-9]{3})|(40[0-8][0-9])|(4090))(-((1[0-9]{1,2})|([2-9][0-9]{0,2})|([1-3][0-9]{3})|(40[0-8][0-9])|(4090)))?)?)*";
      length "1..253";
    }
    description
      "The definition for specifying the vlan range.";
  }

  typedef min-group-id {
    type uint32;
  }

  typedef max-group-id {
    type uint32;
  }

  typedef interface-value-type {
    type string {
      pattern "(((([0-9]|1[0-6])/([1-9]|[1-9][0-9])(:[1-4])?)|([1-9]|[1-9][0-9]|[1-4][0-9][0-9]|50[0-9]|51[0-2])))";
    }
  }

  typedef openflow-controller-name-type {
    type name32-type;
  }

  container openflow-global {
    container openflow {
      container enable {
        leaf ofVerType {
          type enumeration {
            enum "ofv13" {
              value 2;
            }
          }
        }
      }
      container default-behavior {
        leaf send-to-controller {
          type empty;
        }
      }
      container mirror {
        container destination {
          list mirror-interface {
            key "interface-type interface-value";
            leaf interface-type {
              type enumeration {
                enum "ethernet" {
                  value 1;
                }
              }
            }
            leaf interface-value {
              type interface-value-type;
            }
          }
        }
      }
      list controller {
        key "controller-name";
        description
          "OpenFlow controller configuration";
        leaf controller-name {
          type openflow-controller-name-type;
          description
            "OpenFlow controller name";
        }
        container passive {
          description
            "OpenFlow passive controller configuration";
          leaf passive-connection-method {
            type enumeration {
              enum "no-ssl" {
                value 1;
              }
            }
            description
              "This parameter defines the connection method to be
               used to connect to OpenFlow controller. By default no-ssl is
               used";
          }
          leaf passive-controller-address {
            type inet:ip-address;
            description
              "IP address passive of the OpenFlow controller. Only IPv4 address
               is supported.";
          }
          leaf passive-connection-port {
            type uint32 {
              range "1..65535";
            }
            description
              "TCP port number for the OpenFlow controller.";
          }
          leaf passive-controller-vrf {
            type common-def:vrf-name;
          }
        }
        container active-controller {
          leaf controller-address {
            type inet:ip-address;
            description
              "IP address active of the OpenFlow controller. Only IPv4 address
               is supported.";
          }
          leaf connection-method {
            type enumeration {
              enum "no-ssl" {
                value 1;
              }
              enum "ssl" {
                value 2;
              }
            }
            description
              "This parameter defines the connection method to be
               used to connect to OpenFlow controller. By default no-ssl is
               used";
          }
          leaf connection-port {
            type uint32 {
              range "1..65535";
            }
            description
              "TCP port number for the OpenFlow controller.";
          }
          leaf active-controller-vrf {
            type common-def:vrf-name;
          }
        }
      }
      container ingress-replication {
        when "(/c:capabilities/c:openflow/c:ingress = \"true\")";
        container group-id-range {
          leaf min-group-id {
            type min-group-id;
          }
          leaf max-group-id {
            type max-group-id;
          }
        }
      }
    }
  }

  grouping openflow-interface-cmds {
    container openflow {
      container protected-vlans {
        leaf protected-vlan-add {
          type ui32-vlan-range;
          description
            "This specifies list of vlans to
             be added to openflow.";
        }
        leaf protected-vlan-remove {
          type ui32-vlan-range;
          description
            "This specifies the list of vlans
             to be removed.";
        }
      }
      container enableInterfaceLevel {
        leaf modeType {
          type enumeration {
            enum "layer2" {
              value 1;
            }
            enum "layer3" {
              value 2;
            }
            enum "layer23" {
              value 3;
            }
          }
        }
        leaf hybrid-mode {
          type empty;
        }
      }
    }
  }

  grouping openflow-port-channel-cmds {
    container openflowPo {
      container enablePoMode {
        leaf modeTypePo {
          type enumeration {
            enum "egress" {
              value 1;
            }
          }
        }
      }
    }
  }

  augment "/interface:interface/interface:ethernet" {
    uses openflow-interface-cmds;
  }
  augment "/interface:interface/interface:port-channel" {
    uses openflow-port-channel-cmds;
  }
}
